(defun EL:PowerValid (record / w)
  (setq w (EL:Get 'watts record))
  (and (member (EL:Get 'category record) '(lighting sign exit other))
       (equal (type (EL:Get 'display record)) 'STR) (/= (EL:Get 'display record) "")
       (equal (type w) 'INT) (>= w 0) (or (> w 0) (equal (EL:Get 'zero-confirmed record) T))))
(defun EL:PowerShape (record)
  (and (EL:OnlyKeys record '(identity category display watts zero-confirmed source))
       (listp (EL:Get 'identity record)) (= (length (EL:Get 'identity record)) 3)
       (equal (type (car (EL:Get 'identity record))) 'STR) (EL:PowerValid record)))
(defun EL:DefaultWatts (category) (cond ((equal category 'lighting) 5) ((member category '(sign exit)) 1)))
(defun EL:ResolvePower (identity current drawing library / record source)
  (cond ((setq record (EL:By 'identity identity current)) (setq source 'current-input))
        ((setq record (EL:By 'identity identity drawing)) (setq source 'drawing-saved))
        ((setq record (EL:By 'identity identity library)) (setq source 'library-saved)))
  (if record (EL:Put 'source source record)))
(defun EL:ParseWatts (s / n valid c)
  (setq n 0 valid (and (equal (type s) 'STR) (> (strlen s) 0)))
  (if valid
    (foreach c (vl-string->list s)
      (if (or (< c 48) (> c 57) (> n 214748364) (and (= n 214748364) (> c 55)))
        (setq valid nil)
        (if valid (setq n (+ (* n 10) (- c 48)))))))
  (if valid n))
(defun EL:LibraryValid (raw)
  (and (EL:OnlyKeys raw '(version devices roles)) (member (EL:Get 'version raw) '(1 2))
    (not (vl-some '(lambda (row) (not (EL:RoleShape row))) (EL:Get 'roles raw)))
    (not (vl-some '(lambda (row) (not (EL:PowerShape row))) (EL:Get 'devices raw)))))
(defun EL:LoadLibrary (/ raw result)
  (setq raw (EL:ReadData (strcat *EL:LiteDataRoot* "config/device-library.eld")))
  (if raw
    (progn
      (setq result (vl-catch-all-apply 'EL:LibraryValid (list raw)))
      (if (and (not (vl-catch-all-error-p result)) result) (EL:Get 'devices raw)
        (progn (princ "\n项目设备库失效；已保存的无效值不会参与计算，请核对配置。") nil)))))
(defun EL:CountRows (circuit blocks excluded / rows id block identity row)
  (foreach id (EL:Unique (EL:Get 'devices circuit))
    (setq block (EL:By 'id id blocks))
    (if (and block (equal (EL:Get 'role block) 'device) (not (member id excluded)))
      (progn
        (setq identity (EL:Get 'identity block) row (EL:By 'identity identity rows))
        (if row
          (setq rows (subst (EL:Put 'ids (cons id (EL:Get 'ids row)) (EL:Put 'count (1+ (EL:Get 'count row)) row)) row rows))
          (setq rows (cons (list (cons 'identity identity) (cons 'name (EL:Get 'name block))
            (cons 'count 1) (cons 'ids (list id))) rows)))))) (reverse rows))
(defun EL:OwnershipConflicts (circuits / counts circuit id conflicts row)
  (foreach circuit circuits
    (foreach id (EL:Unique (EL:Get 'devices circuit))
      (setq counts (EL:Put id (cons (EL:Get 'id circuit) (EL:Get id counts)) counts))))
  (foreach row counts (if (> (length (cdr row)) 1) (setq conflicts (cons (car row) conflicts)))) conflicts)
(defun EL:CircuitStatistics (circuit blocks excluded cfg library current / rows out issues row record w total good subtotal)
  (setq rows (EL:CountRows circuit blocks excluded) total 0 good T)
  (foreach row rows
    (setq record (EL:ResolvePower (EL:Get 'identity row) current (EL:Get 'powers cfg) library))
    (if (EL:PowerValid record)
      (progn
        (setq w (EL:Get 'watts record) subtotal nil)
        (if (or (> w (/ 2147483647 (EL:Get 'count row)))
                (> (* w (EL:Get 'count row)) (- 2147483647 total)))
          (setq good nil issues (cons (EL:Issue 'POWER_OVERFLOW (EL:Get 'ids row) w) issues))
          (setq subtotal (* w (EL:Get 'count row)) total (+ total subtotal)))
        (setq row (EL:Put 'watts w row) row (EL:Put 'subtotal subtotal row)
              row (EL:Put 'display (EL:Get 'display record) row) row (EL:Put 'source (EL:Get 'source record) row)))
      (progn
        (setq good nil issues (cons (EL:Issue 'POWER_MISSING_OR_INVALID (EL:Get 'ids row) (EL:Get 'identity row)) issues))))
    (setq out (cons row out)))
  (if (vl-some '(lambda (id) (member id excluded)) (EL:Get 'devices circuit))
    (setq good nil issues (cons (EL:Issue 'DEVICE_OWNERSHIP_CONFLICT (EL:Get 'id circuit) excluded) issues)))
  (if (> total 172)
    (setq issues (cons (EL:Issue 'POWER_OVER_LIMIT (EL:Get 'devices circuit)
      (list (cons 'circuit (EL:Get 'id circuit)) (cons 'watts total) (cons 'counts (reverse out)))) issues)))
  (setq circuit (EL:Put 'power-values-complete good circuit))
  (setq good (and good (EL:Get 'complete circuit)))
  (setq circuit (EL:Put 'counts (reverse out) circuit) circuit (EL:Put 'watts total circuit)
        circuit (EL:Put 'power-complete good circuit) circuit (EL:Put 'power-issues (reverse issues) circuit)
        circuit (EL:Put 'over-limit (> total 172) circuit))
  (EL:Put 'power-status (cond ((not good) 'incomplete) ((> total 172) 'over-limit) (T 'pass)) circuit))
;; Date: 2026-10-13. Pure per-circuit reuse; never caches a DWG freshness decision.
(defun EL:StatisticsCircuitInput (circuit)
  (vl-remove-if '(lambda (pair) (member (car pair)
    '(counts watts power-values-complete power-complete power-issues over-limit power-status))) circuit))
(defun EL:CircuitStatisticsScoped (circuit blocks excluded cfg library current / identities row key cached value)
  (if (not *EL:StatisticsScopeEnabled*)
    (EL:CircuitStatistics circuit blocks excluded cfg library current)
    (progn
      (foreach row (EL:CountRows circuit blocks excluded)
        (setq identities (cons (EL:Get 'identity row) identities)))
      (setq key (list (EL:StatisticsCircuitInput circuit) blocks excluded
        (vl-remove-if '(lambda (pair) (member (car pair) '(powers template))) cfg)
        (vl-remove-if-not '(lambda (pair) (member (EL:Get 'identity pair) identities)) (EL:Get 'powers cfg))
        library current)
        cached (assoc key *EL:StatisticsMemo*))
      (if cached (progn (setq value (cdr cached)) (EL:PerfCount "statistics-circuits-reused" 1))
        (progn (setq value (EL:CircuitStatistics circuit blocks excluded cfg library current))
          (EL:PerfCount "statistics-circuits-computed" 1)))
      (setq *EL:StatisticsNext* (cons (cons key value) *EL:StatisticsNext*)) value)))
(defun EL:BoxStatistics (result cfg library current / excluded circuits circuit total allowed overflow *EL:StatisticsNext*)
  (setq excluded (EL:OwnershipConflicts (EL:Get 'circuits result)) total 0 allowed (EL:Get 'complete result))
  (foreach circuit (EL:Get 'circuits result)
    (setq circuit (EL:CircuitStatisticsScoped circuit (EL:Get 'blocks (EL:Get 'snapshot result)) excluded cfg library current))
    (if (EL:Get 'power-complete circuit)
      (if (> (EL:Get 'watts circuit) (- 2147483647 total)) (setq overflow T allowed nil)
        (setq total (+ total (EL:Get 'watts circuit)))))
    (if (not (equal (EL:Get 'power-status circuit) 'pass)) (setq allowed nil))
    (setq circuits (cons circuit circuits)))
  (if *EL:StatisticsScopeEnabled* (setq *EL:StatisticsMemo* (reverse *EL:StatisticsNext*)))
  (setq result (EL:Put 'circuits (reverse circuits) result) result (EL:Put 'box-watts total result)
        result (EL:Put 'power-config (list (EL:Get 'powers cfg) library current) result)
        result (EL:Put 'device-conflicts excluded result) result (EL:Put 'box-total-overflow overflow result))
  (EL:Put 'can-generate (and circuits allowed) result))
(defun EL:PowerTableRows (result / rows circuit row old)
  (foreach circuit (EL:Get 'circuits result)
    (foreach row (EL:Get 'counts circuit)
      (setq old (EL:By 'identity (EL:Get 'identity row) rows))
      (if old
        (setq rows (subst (EL:Put 'circuits (cons (list (EL:Get 'id circuit) (EL:Get 'count row)) (EL:Get 'circuits old))
          (EL:Put 'ids (EL:Unique (append (EL:Get 'ids old) (EL:Get 'ids row)))
            (EL:Put 'count (+ (EL:Get 'count row) (EL:Get 'count old)) old))) old rows))
        (setq rows (cons (EL:Put 'circuits (list (list (EL:Get 'id circuit) (EL:Get 'count row))) row) rows)))))
  (reverse rows))
(defun EL:PrintStatistics (result / circuit row)
  (foreach circuit (EL:Get 'circuits result)
    (princ (strcat "\n" (EL:Get 'id circuit) "：" (itoa (EL:Get 'watts circuit)) "W，"
      (cond ((equal (EL:Get 'power-status circuit) 'pass) "合格") ((equal (EL:Get 'power-status circuit) 'over-limit) "超过172W") (T "未完整／功率缺项"))))
    (foreach row (EL:Get 'counts circuit)
      (princ (strcat "\n  " (EL:Get 'name row) " × " (itoa (EL:Get 'count row)) "，"
        (if (EL:Get 'watts row) (strcat (itoa (EL:Get 'watts row)) "W/个") "功率未确认"))))
    (foreach row (EL:Get 'power-issues circuit) (princ (strcat "\n  " (vl-prin1-to-string row)))))
  (princ (strcat "\n已完整识别且功率齐全的回路合计：" (itoa (EL:Get 'box-watts result)) "W。"))
  (if (EL:Get 'box-total-overflow result) (princ "\n合计超出整数范围，上述为部分小计；正式生成禁用。"))
  (if (not (EL:Get 'can-generate result)) (princ "\n存在未解决识别／功率问题或超过 172W，正式生成已禁用。")))
(princ)

(defun EL:MergePowers (saved edits / row old)
  (foreach row edits
    (setq old (EL:By 'identity (EL:Get 'identity row) saved)
          saved (if old (subst row old saved) (cons row saved))))
  saved)
(defun EL:SavePowerLibrary (edits / path raw checked devices)
  (setq path (strcat *EL:LiteDataRoot* "config/device-library.eld") raw (EL:ReadData path))
  (setq checked (if raw (vl-catch-all-apply 'EL:LibraryValid (list raw)) (not (findfile path))))
  (if (and checked (not (vl-catch-all-error-p checked)))
    (progn
      (setq devices (EL:MergePowers (EL:Get 'devices raw) edits))
      (EL:WriteData path (list (cons 'version 2) (cons 'devices devices) (cons 'roles (EL:Get 'roles raw)))))
    (progn (princ "\n设备库无效，保留原文件；本图功率不受影响。") nil)))

(defun EL:LoadRoleLibrary (/ raw checked)
  (if *EL:Root*
    (progn
      (setq raw (EL:ReadData (strcat *EL:LiteDataRoot* "config/device-library.eld")))
      (if raw
        (progn (setq checked (vl-catch-all-apply 'EL:LibraryValid (list raw)))
          (if (and checked (not (vl-catch-all-error-p checked))) (EL:Get 'roles raw)))))))
(defun EL:SaveRoleLibrary (edits / raw path checked row old roles)
  (setq path (strcat *EL:LiteDataRoot* "config/device-library.eld") raw (EL:ReadData path)
        checked (if raw (vl-catch-all-apply 'EL:LibraryValid (list raw)) (not (findfile path))))
  (if (and checked (not (vl-catch-all-error-p checked)))
    (progn
      (setq roles (EL:Get 'roles raw))
      (foreach row edits
        (setq old (EL:By 'identity (EL:Get 'identity row) roles)
              roles (if old (subst row old roles) (cons row roles))))
      (EL:WriteData path (list (cons 'version 2) (cons 'devices (EL:Get 'devices raw)) (cons 'roles roles))))
    (progn (princ "\n设备库无效，角色未写入设备库；原文件保留。") nil)))

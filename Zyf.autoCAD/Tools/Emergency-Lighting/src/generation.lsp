(defun EL:LocalPoint (p origin rotation scale / x y c s)
  (setq x (* scale (car p)) y (* scale (cadr p)) c (cos rotation) s (sin rotation))
  (EL:V+ origin (list (- (* c x) (* s y)) (+ (* s x) (* c y)) (* scale (caddr p)))))
(defun EL:InversePoint (p m / v det)
  (setq v (EL:V- p (list (nth 4 m) (nth 5 m) (nth 6 m)))
        det (- (* (nth 0 m) (nth 3 m)) (* (nth 1 m) (nth 2 m))))
  (if (and (> (abs det) 1.0e-12) (> (abs (nth 7 m)) 1.0e-12))
    (list (/ (- (* (nth 3 m) (car v)) (* (nth 2 m) (cadr v))) det)
          (/ (- (* (nth 0 m) (cadr v)) (* (nth 1 m) (car v))) det) (/ (caddr v) (nth 7 m)))))
(defun EL:ReplaceAll (textdata token value / index offset out)
  (setq offset 0 out "")
  (while (setq index (vl-string-search token textdata offset))
    (setq out (strcat out (substr textdata (1+ offset) (- index offset)) value) offset (+ index (strlen token))))
  (strcat out (substr textdata (1+ offset))))
(defun EL:FormatValid (formattext / cleaned token)
  (if (equal (type formattext) 'STR)
    (progn
      (setq cleaned formattext)
      (foreach token '("{回路功率W}" "{回路编号}" "{设备数量摘要}") (setq cleaned (EL:ReplaceAll cleaned token "")))
      (and (not (vl-string-search "{" cleaned)) (not (vl-string-search "}" cleaned))
           (vl-string-search "{回路功率W}" formattext)))))
(defun EL:CountSummary (circuit / textdata row)
  (setq textdata "")
  (foreach row (EL:Get 'counts circuit)
    (setq textdata (strcat textdata (if (= textdata "") "" "、")
      (cond ((EL:Get 'display row)) ((EL:Get 'name row)) (T "设备")) "×" (itoa (EL:Get 'count row))))) textdata)
(defun EL:FormatCircuitText (formattext label circuit)
  (EL:ReplaceAll (EL:ReplaceAll (EL:ReplaceAll formattext "{回路功率W}" (itoa (EL:Get 'watts circuit)))
    "{回路编号}" label) "{设备数量摘要}" (EL:CountSummary circuit)))
(defun EL:State (option definition) (EL:By 'option option (EL:Get 'states definition)))
(defun EL:ContourValid (segments / good seg)
  (setq good (and (listp segments) segments))
  (foreach seg segments (if (not (and (listp seg) (= (length seg) 2) (EL:Point (car seg)) (EL:Point (cadr seg)))) (setq good nil))) good)
(defun EL:TemplateValid (template / panel circuit good def state option textspec)
  (setq panel (EL:Get 'panel template) circuit (EL:Get 'circuit template)
        good (and (EL:OnlyKeys template '(panel circuit step actual-format reserve-format layer))
          (EL:Point (EL:Get 'step template)) (> (EL:Norm (EL:Get 'step template)) 1.0e-9)
          (EL:FormatValid (EL:Get 'actual-format template))
          (equal (type (EL:Get 'reserve-format template)) 'STR) (/= (EL:Get 'reserve-format template) "")
          (equal (type (EL:Get 'layer template)) 'STR) (/= (EL:Get 'layer template) "")))
  (foreach def (list panel circuit)
    (if (not (and (EL:OnlyKeys def '(name property definition states source-handle))
                  (equal (type (EL:Get 'name def)) 'STR) (equal (type (EL:Get 'property def)) 'STR)
                  (equal (type (EL:Get 'definition def)) 'STR) (= (length (EL:Get 'states def)) 3)
                  (= (length (EL:Unique (mapcar '(lambda (s) (EL:Get 'value s)) (EL:Get 'states def)))) 3))) (setq good nil))
    (foreach state (EL:Get 'states def)
      (if (not (and (EL:OnlyKeys state '(option value connection contour text)) (EL:ContourValid (EL:Get 'contour state))
           (or (equal (type (EL:Get 'value state)) 'STR) (EL:Number (EL:Get 'value state))))) (setq good nil))))
  (foreach option '(cap300 cap600 cap1000)
    (setq state (EL:State option panel))
    (if (not (and state (EL:Point (EL:Get 'connection state)) (EL:Get 'contour state))) (setq good nil)))
  (foreach option '(normal ground reserve)
    (setq state (EL:State option circuit) textspec (EL:Get 'text state))
    (if (not (and state (EL:Point (EL:Get 'connection state)) (EL:Get 'contour state)
      (EL:Point (EL:Get 'offset textspec)) (member (EL:Get 'type textspec) '("TEXT" "MTEXT"))
      (EL:OnlyKeys textspec '(offset type style height width align rotation factor oblique layer))
      (or (not (assoc 'layer textspec))
        (and (equal (type (EL:Get 'layer textspec)) 'STR) (/= (EL:Get 'layer textspec) "")))
      (equal (type (EL:Get 'style textspec)) 'STR) (EL:Number (EL:Get 'height textspec)) (> (EL:Get 'height textspec) 0)
      (EL:Number (EL:Get 'rotation textspec)) (EL:NonNegative (EL:Get 'width textspec))
      (EL:Number (EL:Get 'factor textspec)) (> (EL:Get 'factor textspec) 0.0)
      (EL:Number (EL:Get 'oblique textspec)) (< (abs (EL:Get 'oblique textspec)) (/ pi 2.0))
      (equal (type (EL:Get 'align textspec)) 'INT)
      (if (= (EL:Get 'type textspec) "TEXT") (member (EL:Get 'align textspec) '(0 1 2 4 6 7 8 9 10 11 12 13 14))
        (member (EL:Get 'align textspec) '(1 2 3 4 5 6 7 8 9))))) (setq good nil))) good)
(defun EL:BuildGenerationPlan (result template capacity outputs origin rotation scale / good actual seen labels output id circuit mode state panelstate rows index target position annotation textdata)
  (setq good (and (EL:Get 'can-generate result) (EL:TemplateValid template) (EL:Point origin)
          (EL:Number rotation) (EL:Number scale) (> scale 0.0))
        actual (mapcar '(lambda (c) (EL:Get 'id c)) (EL:Get 'circuits result))
        panelstate (EL:State capacity (EL:Get 'panel template)) index 0)
  (if (not panelstate) (setq good nil))
  (foreach output outputs
    (setq id (EL:Get 'circuit-id output) mode (EL:Get 'mode output) circuit (EL:By 'id id (EL:Get 'circuits result))
          state (EL:State mode (EL:Get 'circuit template)))
    (if (or (not state) (member (EL:Get 'label output) labels)
            (not (equal (type (EL:Get 'label output)) 'STR)) (= (EL:Get 'label output) "")) (setq good nil))
    (setq labels (cons (EL:Get 'label output) labels))
    (if id
      (if (and circuit (member mode '(normal ground)) (not (member id seen))) (setq seen (cons id seen)) (setq good nil))
      (if (not (equal mode 'reserve)) (setq good nil)))
    (if (and good state panelstate)
      (progn
        (setq target (EL:LocalPoint (EL:V+ (EL:Get 'connection panelstate) (EL:V* index (EL:Get 'step template))) origin rotation scale)
              position (EL:V- target (EL:LocalPoint (EL:Get 'connection state) '(0.0 0.0 0.0) rotation scale))
              annotation (EL:Get 'text state)
              textdata (if id (EL:FormatCircuitText (EL:Get 'actual-format template) (EL:Get 'label output) circuit)
                (EL:Get 'reserve-format template)))
        (setq rows (cons (list (cons 'circuit-id id) (cons 'label (EL:Get 'label output)) (cons 'mode mode)
          (cons 'value (EL:Get 'value state)) (cons 'position position) (cons 'connection target)
          (cons 'contour (EL:Get 'contour state)) (cons 'annotation annotation)
          (cons 'text-position (EL:LocalPoint (EL:Get 'offset annotation) position rotation scale)) (cons 'text textdata)
          (cons 'watts (if id (EL:Get 'watts circuit)))) rows))))
    (setq index (1+ index)))
  (if (or (/= (length seen) (length actual)) (vl-some '(lambda (id) (not (member id seen))) actual)) (setq good nil))
  (if good
    (list (cons 'panel-name (EL:Get 'name (EL:Get 'panel template))) (cons 'panel-value (EL:Get 'value panelstate))
          (cons 'panel-contour (EL:Get 'contour panelstate)) (cons 'position origin) (cons 'capacity capacity)
          (cons 'rotation rotation) (cons 'scale scale) (cons 'rows (reverse rows)))))
;; Date: 2026-10-09. AllowedValues may contain VARIANT elements inside the array.
(defun EL:DynamicValueData (value)
  (cond
    ((equal (type value) 'VARIANT) (EL:DynamicValueData (vlax-variant-value value)))
    ((equal (type value) 'SAFEARRAY) (EL:DynamicValueData (vlax-safearray->list value)))
    ((listp value) (mapcar 'EL:DynamicValueData value))
    (T value)))
(defun EL:AllowedValues (property / value)
  (setq value (EL:DynamicValueData (vlax-get-property property 'AllowedValues)))
  (if (listp value) value))
(defun EL:DynamicProperty (object name / result property)
  (if (= (vla-get-IsDynamicBlock object) :vlax-true)
    (foreach property (vlax-invoke object 'GetDynamicBlockProperties)
      (if (= (vla-get-PropertyName property) name) (setq result property)))) result)
(defun EL:SetDynamicValue (object name value / property)
  (setq property (EL:DynamicProperty object name))
  (if (and property (= (vla-get-ReadOnly property) :vlax-false) (member value (EL:AllowedValues property)))
    (progn
      (EL:PerfWrite 'vla-put-Value (list property (vlax-make-variant value (vlax-variant-type (vla-get-Value property)))))
      (equal value (vlax-variant-value (vla-get-Value property)) 1.0e-9))))
(defun EL:CaptureText (block / pick data obj typ matrix point scale align)
  (if (setq pick (EL:PickEntity "\n拾取该档位的统计文字样本（TEXT/MTEXT）: "))
    (progn
      (setq data (entget (car pick)) typ (cdr (assoc 0 data)) obj (vlax-ename->vla-object (car pick))
            matrix (EL:InsertMatrix block) scale (abs (cdr (assoc 42 (entget block)))))
      (if (member typ '("TEXT" "MTEXT"))
        (progn
          (setq align (if (= typ "TEXT") (vla-get-Alignment obj) (vla-get-AttachmentPoint obj)))
          (if (or (= typ "MTEXT") (not (member align '(3 5))))
            (progn
              (setq point (vlax-safearray->list (vlax-variant-value
                (if (and (= typ "TEXT") (/= align 0)) (vla-get-TextAlignmentPoint obj) (vla-get-InsertionPoint obj)))))
              (list (cons 'offset (EL:InversePoint point matrix)) (cons 'type typ) (cons 'style (vla-get-StyleName obj))
                    (cons 'height (/ (if (= typ "TEXT") (vla-get-Height obj) (vla-get-TextHeight obj)) scale))
                    (cons 'width (if (= typ "MTEXT") (/ (vla-get-Width obj) scale) 0.0))
                    (cons 'align align) (cons 'rotation (- (vla-get-Rotation obj) (cdr (assoc 50 (entget block)))))
                    (cons 'factor (if (= typ "TEXT") (vla-get-ScaleFactor obj) 1.0))
                    (cons 'oblique (if (= typ "TEXT") (vla-get-ObliqueAngle obj) 0.0))))))))))
(defun EL:CaptureTemplate (options kind cfg / name propertyname definition states pick e obj props property index i choice point matrix contour state option annotation valid lastblock)
  (setq valid T)
  (foreach option options
    (if valid
      (progn
        (setq pick (EL:PickEntity (strcat "\n拾取已显示 " (EL:OptionLabel option) " 档位的" kind "动态块: ")))
        (if (and pick (= (cdr (assoc 0 (entget (car pick)))) "INSERT"))
          (progn
            (setq e (car pick) obj (vlax-ename->vla-object e) matrix (EL:InsertMatrix e))
            (if (and matrix (= (vla-get-IsDynamicBlock obj) :vlax-true)
                     (> (vla-get-XScaleFactor obj) 0.0)
                     (equal (vla-get-XScaleFactor obj) (vla-get-YScaleFactor obj) 1.0e-9))
              (progn
                (if (not name)
                  (progn
                    (setq name (EL:EffectiveName e) definition (EL:Signature (EL:DefinitionData name nil))
                          props (vlax-invoke obj 'GetDynamicBlockProperties) i 0)
                    (foreach property props
                      (setq i (1+ i))
                      (princ (strcat "\n" (itoa i) " " (vla-get-PropertyName property) "："
                        (vl-prin1-to-string (EL:AllowedValues property)))))
                    (setq index (getint "\n选择档位属性序号（查看真实属性和允许值）: "))
                    (if (and index (> index 0) (<= index (length props)))
                      (setq propertyname (vla-get-PropertyName (nth (1- index) props))))))
                (setq property (EL:DynamicProperty obj propertyname))
                (if (and property (equal name (EL:EffectiveName e)) (= (vla-get-ReadOnly property) :vlax-false)
                         (member (vlax-variant-value (vla-get-Value property)) (EL:AllowedValues property)))
                  (progn
                    (setq point (getpoint "\n点选接线定位点（箱体为首回路连接点；回路为接入点）: ")
                          contour (EL:BlockContour e '(1.0 0.0 0.0 1.0 0.0 0.0 0.0 1.0)
                            (max 0.000001 (EL:Get 'eps_boundary (EL:Get 'params cfg))) nil))
                    (if (and point (not (EL:Get 'issues contour)))
                      (progn
                        (setq state (list (cons 'option option) (cons 'value (vlax-variant-value (vla-get-Value property)))
                          (cons 'connection (EL:InversePoint (trans point 1 0) matrix))
                          (cons 'contour (mapcar '(lambda (seg) (list (EL:InversePoint (car seg) matrix) (EL:InversePoint (cadr seg) matrix)))
                            (EL:Get 'segments contour)))))
                        (if (= kind "回路")
                          (if (setq annotation (EL:CaptureText e)) (setq state (EL:Put 'text annotation state)) (setq valid nil)))
                        (setq states (cons state states) lastblock e))
                      (setq valid nil)))
                  (setq valid nil)))
              (setq valid nil)))
          (setq valid nil)))))
  (if valid (list (list (cons 'name name) (cons 'property propertyname) (cons 'definition definition)
    (cons 'source-handle (cdr (assoc 5 (entget lastblock)))) (cons 'states (reverse states))) lastblock)
    (princ "\n模板采集未完成；需同一动态块定义、真实可写属性、正等比样本和可解析轮廓。")))
(defun EL:OutputLayerReady (layer / data)
  (setq data (tblsearch "LAYER" layer))
  (or (not data) (and (= 0 (logand 5 (cdr (assoc 70 data)))) (> (cdr (assoc 62 data)) 0))))
(defun EL:TemplateRuntimeValid (template cfg / good definition b obj property state layer style)
  (setq good (EL:TemplateValid template) layer (EL:Get 'layer template))
  (if good
    (progn
      (if (and (not (equal (EL:Get 'name (EL:Get 'panel template)) "ZYF_Tool_应急照明配电箱图块"))
          (member layer (append (EL:Get 'wire-layers cfg) (EL:Get 'panel-layers cfg)
            (EL:Get 'device-layers cfg) (EL:Get 'leader-layers cfg)))) (setq good nil))
      (foreach definition (list (EL:Get 'panel template) (EL:Get 'circuit template))
        (if (or (not (tblsearch "BLOCK" (EL:Get 'name definition)))
            (not (equal (EL:Get 'definition definition) (EL:Signature (EL:DefinitionData (EL:Get 'name definition) nil)))))
          (setq good nil))
        (if (member (EL:Get 'name definition) '("ZYF_Tool_应急照明配电箱图块" "ZYF_Tool_应急照明配电回路图块"))
          (if (not (EL:WithFixedBlock (EL:Get 'name definition) 'EL:FixedDefinitionValid (list definition))) (setq good nil))
          (if (and (EL:Get 'source-handle definition) (setq b (handent (EL:Get 'source-handle definition)))
              (equal (cdr (assoc 0 (entget b))) "INSERT") (equal (EL:EffectiveName b) (EL:Get 'name definition)))
            (progn
              (setq obj (vlax-ename->vla-object b) property (EL:DynamicProperty obj (EL:Get 'property definition)))
              (if (and property (= (vla-get-ReadOnly property) :vlax-false))
                (foreach state (EL:Get 'states definition)
                  (if (not (member (EL:Get 'value state) (EL:AllowedValues property))) (setq good nil)))
                (setq good nil)))
            (setq good nil))))
      (foreach state (EL:Get 'states (EL:Get 'circuit template))
        (setq style (EL:Get 'text state))
        (if (not (tblsearch "STYLE" (EL:Get 'style style))) (setq good nil))
        (if (and (EL:Get 'layer style) (not (EL:OutputLayerReady (EL:Get 'layer style)))) (setq good nil)))
      (and good (EL:OutputLayerReady layer)))))
(defun EL:LegacyTemplate (/ *error* cfg panel circuit anchor next step formattext reserve layer template)
  (defun *error* (msg)
    (EL:ClearPickHighlights)
    (if msg (princ (strcat "\n模板采集取消，拾取亮显已清理：" msg))) (princ))
  (EL:ClearPickHighlights)
  (if (and (setq cfg (EL:LoadConfig)) (EL:ParamsValid (EL:Get 'params cfg)))
    (progn
      (setq panel (EL:CaptureTemplate '(cap300 cap600 cap1000) "箱体" cfg))
      (if panel (setq circuit (EL:CaptureTemplate '(normal ground reserve) "回路" cfg)))
      (if (and panel circuit)
        (progn
          (setq anchor (getpoint "\n在最后选取的箱体样本上点选首回路接入位置: "))
          (if anchor (setq next (getpoint anchor "\n点选相邻下一回路接入位置（确定排列向量）: ")))
          (if (and anchor next)
            (progn
              (setq step (EL:V- (EL:InversePoint (trans next 1 0) (EL:InsertMatrix (cadr panel)))
                               (EL:InversePoint (trans anchor 1 0) (EL:InsertMatrix (cadr panel))))
                    formattext (getstring T "\n实际回路文字模板 <{回路功率W}W>: ")
                    reserve (getstring T "\n预留回路文字 <预留>: ") layer (getstring T "\n系统图输出图层 <EL-SYSTEM>: ")
                    template (list (cons 'panel (car panel)) (cons 'circuit (car circuit)) (cons 'step step)
                      (cons 'actual-format (if (= formattext "") "{回路功率W}W" formattext))
                      (cons 'reserve-format (if (= reserve "") "预留" reserve)) (cons 'layer (if (= layer "") "EL-SYSTEM" layer))))
              (if (EL:TemplateRuntimeValid template cfg)
                (EL:SaveConfig (EL:Put 'template template cfg))
                (princ "\n模板字段、样本定义、文字样式或输出图层校验失败，未保存。"))))))))
  (EL:ClearPickHighlights) (princ))
(defun EL:ChooseOutputs (result / circuits order textdata parsed count i circuit label mode outputs reserve good seen)
  (setq circuits (EL:Get 'circuits result) count (length circuits) i 0)
  (foreach circuit circuits (setq i (1+ i)) (princ (strcat "\n" (itoa i) " = " (EL:Get 'id circuit) " / " (itoa (EL:Get 'watts circuit)) "W")))
  (setq textdata (getstring T "\n按显示序号输入输出顺序，如 3 1 2（Enter 原顺序）: "))
  (if (= textdata "")
    (progn (setq i 1) (repeat count (setq order (append order (list i)) i (1+ i))))
    (progn
      (setq parsed (vl-catch-all-apply 'read (list (strcat "(" textdata ")"))))
      (if (not (vl-catch-all-error-p parsed)) (setq order parsed))))
  (setq good (and (listp order) (= (length order) count)))
  (foreach i order (if (not (and (equal (type i) 'INT) (> i 0) (<= i count) (not (member i seen)))) (setq good nil)) (setq seen (cons i seen)))
  (if good
    (progn
      (foreach i order
        (setq circuit (nth (1- i) circuits) label (getstring T (strcat "\n回路编号 <" (EL:Get 'id circuit) ">: ")))
        (initget "Normal Ground") (setq mode (getkword "\n实际回路档位 [Normal普通/Ground地面] <Normal>: "))
        (setq outputs (append outputs (list (list (cons 'circuit-id (EL:Get 'id circuit))
          (cons 'label (if (= label "") (EL:Get 'id circuit) label)) (cons 'mode (if (equal mode "Ground") 'ground 'normal)))))))
      (initget 4) (setq reserve (getint "\n新增预留回路数 <0>: ") i 0)
      (repeat (cond (reserve) (T 0))
        (setq i (1+ i) outputs (append outputs (list (list (cons 'circuit-id nil) (cons 'label (strcat "RES" (itoa i))) (cons 'mode 'reserve))))))
      outputs)
    (princ "\n顺序必须包含每条实际回路一次。")))
(defun EL:PreviewPlan (plan / row seg)
  (redraw)
  (foreach seg (EL:Get 'panel-contour plan)
    (EL:DrawTransient (EL:LocalPoint (car seg) (EL:Get 'position plan) (EL:Get 'rotation plan) (EL:Get 'scale plan))
      (EL:LocalPoint (cadr seg) (EL:Get 'position plan) (EL:Get 'rotation plan) (EL:Get 'scale plan)) 4))
  (foreach row (EL:Get 'rows plan)
    (foreach seg (EL:Get 'contour row)
      (EL:DrawTransient (EL:LocalPoint (car seg) (EL:Get 'position row) (EL:Get 'rotation plan) (EL:Get 'scale plan))
        (EL:LocalPoint (cadr seg) (EL:Get 'position row) (EL:Get 'rotation plan) (EL:Get 'scale plan)) 3))
    (princ (strcat "\n" (EL:Get 'label row) " / " (EL:OptionLabel (EL:Get 'mode row)) " / "
      (cond ((EL:Get 'text row)) (T "无功率文字"))))
    (if (EL:Get 'text-position row)
      (EL:DrawTransient (EL:Get 'text-position row) (EL:V+ (EL:Get 'text-position row) (list (EL:Get 'scale plan) 0.0 0.0)) 2))))
(defun EL:RollbackCreated (/ object)
  (foreach object *EL:Created* (vl-catch-all-apply 'vla-Delete (list object)))
  (setq *EL:Created* nil))
(defun EL:CreateBlock (space name position scale rotation property value layer / object)
  (EL:PerfCount "block-create-attempts" 1)
  (setq object (EL:PerfWrite 'vla-InsertBlock (list space (vlax-3d-point position) name scale scale scale rotation))
        *EL:Created* (cons object *EL:Created*))
  (EL:PerfWrite 'vla-put-Layer (list object layer))
  (if (not (EL:SetDynamicValue object property value))
    (progn (princ "\n动态属性不存在、只读、允许值变化或写入回读不一致。") (exit)))
  (if (not (equal position (cdr (assoc 10 (entget (vlax-vla-object->ename object)))) 1.0e-6))
    (progn (princ "\n动态状态切换导致基点漂移，生成停止。") (exit))) object)
(defun EL:CreateAnnotation (space row plan layer / spec object scale rotation position textdata doc)
  (EL:PerfCount "text-create-attempts" 1)
  (setq spec (EL:Get 'annotation row) scale (EL:Get 'scale plan)
        rotation (+ (EL:Get 'rotation plan) (EL:Get 'rotation spec)) position (EL:Get 'text-position row) textdata (EL:Get 'text row))
  (if (EL:Get 'layer spec)
    (progn
      (setq layer (EL:Get 'layer spec) doc (vla-get-ActiveDocument (vlax-get-acad-object)))
      (if (not (tblsearch "LAYER" layer)) (vla-Add (vla-get-Layers doc) layer))))
  (if (= (EL:Get 'type spec) "TEXT")
    (setq object (EL:PerfWrite 'vla-AddText (list space textdata (vlax-3d-point position) (* scale (EL:Get 'height spec)))))
    (progn
      (setq textdata (EL:ReplaceAll (EL:ReplaceAll (EL:ReplaceAll textdata "\\" "\\\\") "{" "\\{") "}" "\\}"))
      (setq object (EL:PerfWrite 'vla-AddMText (list space (vlax-3d-point position) (* scale (max 0.001 (EL:Get 'width spec))) textdata)))))
  (setq *EL:Created* (cons object *EL:Created*))
  (EL:PerfWrite 'vla-put-Layer (list object layer)) (EL:PerfWrite 'vla-put-StyleName (list object (EL:Get 'style spec)))
  (if (EL:Get 'layer spec)
    (progn (EL:PerfWrite 'vla-put-Color (list object 256)) (EL:PerfWrite 'vla-put-Linetype (list object "ByLayer"))
      (EL:PerfWrite 'vla-put-LinetypeScale (list object 1.0)) (EL:PerfWrite 'vla-put-Lineweight (list object -1))
      (if (= (EL:Get 'type spec) "TEXT")
        (progn (EL:PerfWrite 'vla-put-Thickness (list object 0.0)) (EL:PerfWrite 'vla-put-TextGenerationFlag (list object 0))))))
  (if (= (EL:Get 'type spec) "TEXT") (EL:PerfWrite 'vla-put-Height (list object (* scale (EL:Get 'height spec))))
    (EL:PerfWrite 'vla-put-TextHeight (list object (* scale (EL:Get 'height spec)))))
  (EL:PerfWrite 'vla-put-Rotation (list object rotation))
  (if (= (EL:Get 'type spec) "TEXT")
    (progn
      (EL:PerfWrite 'vla-put-Alignment (list object (EL:Get 'align spec)))
      (if (/= (EL:Get 'align spec) 0) (EL:PerfWrite 'vla-put-TextAlignmentPoint (list object (vlax-3d-point position))))
      (EL:PerfWrite 'vla-put-ScaleFactor (list object (EL:Get 'factor spec))) (EL:PerfWrite 'vla-put-ObliqueAngle (list object (EL:Get 'oblique spec))))
    (progn (EL:PerfWrite 'vla-put-AttachmentPoint (list object (EL:Get 'align spec)))
      (EL:PerfWrite 'vla-put-InsertionPoint (list object (vlax-3d-point position))))) object)
(defun EL:GeneratePlan (plan template / *error* doc space layer object undo-open newlayer row handles)
  (defun *error* (msg)
    (EL:RollbackCreated)
    (if newlayer (vl-catch-all-apply 'vla-Delete (list newlayer)))
    (if undo-open (vl-catch-all-apply 'vla-EndUndoMark (list doc)))
    (redraw) (if msg (princ (strcat "\n本次生成已清理：" msg))) (princ))
  (setq doc (vla-get-ActiveDocument (vlax-get-acad-object)) space (vla-get-ModelSpace doc)
        layer (EL:Get 'layer template) *EL:Created* nil)
  (if (or (= 0 (logand 1 (getvar "UNDOCTL"))) (/= 0 (logand 8 (getvar "UNDOCTL"))))
    (progn (princ "\n请先启用 UNDO 并结束已有撤销组，再生成系统图。") (exit)))
  (vla-StartUndoMark doc) (setq undo-open T)
  (if (not (tblsearch "LAYER" layer)) (setq newlayer (vla-Add (vla-get-Layers doc) layer)))
  (EL:CreateBlock space (EL:Get 'panel-name plan) (EL:Get 'position plan) (EL:Get 'scale plan) (EL:Get 'rotation plan)
    (EL:Get 'property (EL:Get 'panel template)) (EL:Get 'panel-value plan) layer)
  (foreach row (EL:Get 'rows plan)
    (EL:CreateBlock space (EL:Get 'name (EL:Get 'circuit template)) (EL:Get 'position row) (EL:Get 'scale plan) (EL:Get 'rotation plan)
      (EL:Get 'property (EL:Get 'circuit template)) (EL:Get 'value row) layer)
    (EL:CreateAnnotation space row plan layer))
  (foreach object *EL:Created* (setq handles (cons (vla-get-Handle object) handles)))
  (vla-EndUndoMark doc) (setq undo-open nil *EL:Created* nil) (redraw)
  handles)
(defun EL:LegacyGenerate (/ *error* cfg library fresh template capacity outputs point rotation scale plan handles record)
  (defun *error* (msg) (redraw) (if msg (princ (strcat "\n生成取消：" msg))) (princ))
  (if (and *EL:Result* (setq cfg (EL:LoadConfig)))
    (progn
      (setq template (EL:Get 'template cfg) library (EL:LoadLibrary)
            fresh (EL:CollectEndpointSnapshot cfg) *EL:Result* (EL:BoxStatistics *EL:Result* cfg library nil))
      (cond
        ((not (EL:SourceCurrent *EL:Result* cfg fresh))
         (princ "\nSOURCE_CHANGED：源图或识别配置已变化，请重新运行 ELSTAT。"))
        ((not (EL:Get 'can-generate *EL:Result*)) (EL:PrintStatistics *EL:Result*))
        ((not (EL:TemplateRuntimeValid template cfg)) (princ "\n模板失效或未采集，请运行 ELTEMPLATE。"))
        (T
         (initget "300 600 1000") (setq capacity (getkword "\n箱体档位 [300即0.3kW/600即0.6kW/1000即1kW] <300>: ")
           capacity (cond ((equal capacity "600") 'cap600) ((equal capacity "1000") 'cap1000) (T 'cap300))
           outputs (EL:ChooseOutputs *EL:Result*) point (getpoint "\n选择系统图插入点: "))
         (if (and outputs point)
           (progn
             (setq point (trans point 1 0) rotation (getreal "\n系统图 WCS 旋转角度（度）<0>: "))
             (initget 6) (setq scale (getreal "\n正等比缩放 <1>: ")
               plan (EL:BuildGenerationPlan *EL:Result* template capacity outputs point
                 (* (/ pi 180.0) (cond (rotation) (T 0.0))) (cond (scale) (T 1.0))))
             (if plan
               (progn
                 (EL:PreviewPlan plan) (initget "Yes No")
                 (if (equal (getkword "\n确认上述档位、顺序、数量与功率并正式生成？[Yes/No] <No>: ") "Yes")
                   (if (equal (EL:Get 'signature fresh) (EL:Get 'signature (EL:CollectEndpointSnapshot cfg)))
                     (if (setq handles (EL:GeneratePlan plan template))
                       (progn
                         (setq record (list (cons 'version 1) (cons 'drawing (EL:DrawingID)) (cons 'date (getvar "CDATE"))
                           (cons 'handles handles) (cons 'plan plan) (cons 'source (EL:Get 'signature fresh))))
                         (EL:WriteData (strcat *EL:LiteDataRoot* "output/generation-" (EL:Hash (EL:DrawingID)) ".eld") record)
                         (princ "\n系统图已生成；一次 UNDO 可撤销本次生成。")))
                     (princ "\nSOURCE_CHANGED：预览后源图发生变化，未生成。")))
                 (redraw))
               (princ "\n输出配置无效；实际回路须完整保留且编号唯一，预留须单独新增。")))))))) (princ))
(princ)

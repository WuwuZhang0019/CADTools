;; Date: 2026-10-11. Name classification after tracing; never changes source geometry or signatures.
(defun EL:DLConnectedBlocks (result / ids circuit)
  (foreach circuit (EL:Get 'circuits result) (setq ids (append (EL:Get 'devices circuit) ids)))
  (vl-remove-if-not '(lambda (b) (member (EL:Get 'id b) ids)) (EL:Get 'blocks (EL:Get 'snapshot result))))
(defun EL:DLReference (name result)
  (EL:By 'key (EL:DLNameKey name) (EL:Get 'items (EL:Get 'device-library result))))
(defun EL:DLOverride (name result)
  (EL:Get (EL:DLNameKey name) (EL:Get 'device-overrides result)))
(defun EL:DLSetOverride (result name key value / override)
  (setq override (EL:DLOverride name result) override (EL:Put key value override))
  (EL:Put 'device-overrides (EL:Put (EL:DLNameKey name) override (EL:Get 'device-overrides result)) result))
(defun EL:DLRefsCover (result / good block reference)
  (setq good T)
  (foreach block (EL:DLConnectedBlocks result)
    (setq reference (EL:DLReference (EL:Get 'name block) result))
    (if (not (and reference (member (EL:Get 'id block) (EL:Get 'ids reference)))) (setq good nil))) good)
(defun EL:DLEffectivePowers (result powers / reference key entry override)
  (foreach reference (EL:Get 'items (EL:Get 'device-library result))
    (setq key (EL:Get 'key reference) entry (EL:Get 'entry reference) override (EL:DLOverride key result))
    (if (EL:Get 'watts-set override) (setq powers (EL:Put key (EL:Get 'watts override) powers))
      (if entry (setq powers (EL:Put key (EL:Get 'watts entry) powers))))) powers)
(defun EL:DLPrepare (result powers snapshot force / previous refs entry old block key reference names ids override metadata saved)
  (setq previous (EL:Get 'device-library result) saved (EL:Get 'items previous))
  (foreach block (EL:DLConnectedBlocks result)
    (setq key (EL:DLNameKey (EL:Get 'name block)))
    (if (not (member key names))
      (progn
        (setq names (cons key names) old (EL:By 'key key saved) entry (EL:DLPowerEntry key snapshot) ids nil)
        (foreach block (EL:DLConnectedBlocks result)
          (if (equal key (EL:DLNameKey (EL:Get 'name block))) (setq ids (cons (EL:Get 'id block) ids))))
        ;; Refresh marked defaults on a new recognition; existing manual values still win.
        ;; Historical values remain displayable if the item was removed or the library moved.
        (setq old (if (and (not force) (EL:Get 'entry old)
          (vl-every '(lambda (id) (member id (EL:Get 'ids old))) ids)
          (or (and entry (not (equal (EL:Get 'library-id old) (EL:Get 'library-id (EL:Get 'catalog snapshot)))))
              (not entry))) old))
        (if old (setq entry (EL:Get 'entry old)))
        (setq reference (if old old
          (list (cons 'key key) (cons 'entry entry)
            (cons 'library-id (if entry (EL:Get 'library-id (EL:Get 'catalog snapshot))))
            (cons 'catalog-revision (if entry (EL:Get 'revision (EL:Get 'catalog snapshot)))))))
        (setq reference (EL:Put 'ids (EL:Unique ids) reference) refs (cons reference refs)
          override (EL:DLOverride key result))
        (if (and force entry)
          (progn (setq result (EL:DLSetOverride result key 'watts-set nil)
            result (EL:DLSetOverride result key 'ground-set nil) override (EL:DLOverride key result))))
        (if (EL:Get 'watts-set override) (setq powers (EL:Put key (EL:Get 'watts override) powers))
          (if entry (setq powers (EL:Put key (EL:Get 'watts entry) powers)) (setq powers (EL:Put key nil powers))))
        (EL:PerfCount (if entry "device-library-matches" "device-library-unknown") (length ids)))))
  (setq metadata (list '(schema . 1) (cons 'items (reverse refs)) (cons 'load-error (if snapshot nil T))))
  (if force
    (setq result (EL:Put 'circuits (mapcar '(lambda (c)
      (if (vl-every '(lambda (id) (setq block (EL:By 'id id (EL:Get 'blocks (EL:Get 'snapshot result))))
          (EL:Get 'entry (EL:By 'key (EL:DLNameKey (EL:Get 'name block)) refs))) (EL:Get 'devices c))
        (EL:Put 'ground-source 'device-library c) c)) (EL:Get 'circuits result)) result)))
  (list (cons 'result (EL:Put 'device-library metadata result)) (cons 'powers powers)))
(defun EL:DLGroundValue (name result / entry override)
  (setq override (EL:DLOverride name result) entry (EL:Get 'entry (EL:DLReference name result)))
  ;; Date: 2026-10-11. The checkbox is the value; untouched means non-ground.
  (cond ((EL:Get 'ground-set override) (list T (EL:Get 'is-ground override)))
    (entry (list T (EL:Get 'is-ground entry))) (T (list T nil))))
(defun EL:DLGround (result / rows circuit good hits id block value)
  (foreach circuit (EL:Get 'circuits result)
    (if (and (equal (EL:Get 'ground-source circuit) 'manual) (not (equal (EL:Get 'ground-rule circuit) 'block-table)))
      (setq rows (cons circuit rows))
      (progn (setq good T hits nil)
        (foreach id (EL:Get 'devices circuit)
          (setq block (EL:By 'id id (EL:Get 'blocks (EL:Get 'snapshot result))) value (EL:DLGroundValue (EL:Get 'name block) result))
          (if (not value) (setq good nil)) (if (cadr value) (setq hits (cons id hits))))
        (setq circuit (EL:Put 'is-ground (if hits T nil) (EL:Put 'ground-source (if (or good hits) 'device-library 'default)
          (EL:Put 'ground-rule 'device-library (EL:Put 'ground-evidence hits circuit)))))
        (setq rows (cons circuit rows))))) (EL:Put 'circuits (reverse rows) result))
(defun EL:DLEvaluate (result powers / rows circuit id block key reference entry override issues pending)
  (setq result (EL:DLGround result))
  (foreach circuit (EL:Get 'circuits result)
    (setq issues nil)
    (foreach id (EL:Get 'devices circuit)
      (setq block (EL:By 'id id (EL:Get 'blocks (EL:Get 'snapshot result))) key (EL:DLNameKey (EL:Get 'name block))
        reference (EL:DLReference key result) entry (EL:Get 'entry reference) override (EL:DLOverride key result))
      (if (and (not entry) (not (and (EL:Get 'watts-set override) (EL:DLInt (EL:Get key powers)))))
        (setq issues (cons (EL:Issue 'DEVICE_LIBRARY_UNKNOWN id (EL:Get 'name block)) issues) pending (cons key pending))))
    (if (EL:Get 'load-error (EL:Get 'device-library result))
      (setq issues (cons (EL:Issue 'DEVICE_LIBRARY_UNAVAILABLE nil *EL:DLError*) issues)))
    (if issues (setq circuit (EL:Put 'power-issues (append (EL:Get 'power-issues circuit) (reverse issues))
      (EL:Put 'power-complete nil (EL:Put 'power-status 'incomplete circuit))) result (EL:Put 'can-generate nil result)))
    (setq rows (cons circuit rows)))
  (EL:Put 'library-pending (EL:Unique pending) (EL:Put 'circuits (reverse rows) result)))
(defun EL:DLMaterialRows (result powers / rows block name reference entry key group row ids value override)
  (foreach block (EL:DLConnectedBlocks result)
    (setq name (EL:DLNameKey (EL:Get 'name block)) reference (EL:DLReference name result) entry (EL:Get 'entry reference)
      value (EL:DLGroundValue name result) override (EL:DLOverride name result)
      group (list (if entry (list (EL:Get 'library-id reference) (EL:Get 'device-id entry)) name) (EL:Get name powers) value)
      row (EL:By 'group group rows))
    (if row
      (progn (setq ids (EL:Unique (cons (EL:Get 'id block) (EL:Get 'ids row))))
        (setq rows (subst (EL:Put 'ids ids (EL:Put 'count (length ids)
          (EL:Put 'manual (if (or (EL:Get 'manual row) (EL:Get 'watts-set override) (EL:Get 'ground-set override)) T nil)
            (EL:Put 'keys (EL:Unique (cons name (EL:Get 'keys row))) row)))) row rows)))
      (setq rows (cons (list (cons 'group group) (cons 'key name) (cons 'keys (list name))
        (cons 'name (if entry (EL:Get 'block-name entry) (EL:Get 'name block)))
        (cons 'display (if entry (EL:Get 'display entry) (EL:Get 'name block))) (cons 'entry entry)
        (cons 'library-id (EL:Get 'library-id reference)) (cons 'count 1) (cons 'ids (list (EL:Get 'id block)))
        (cons 'watts (EL:Get name powers)) (cons 'ground-known (car value)) (cons 'is-ground (cadr value))
        (cons 'manual (if (or (EL:Get 'watts-set override) (EL:Get 'ground-set override)) T nil))) rows))))
  (if rows (vl-sort rows '(lambda (a b) (< (EL:Get 'key a) (EL:Get 'key b))))))
(defun EL:DLPersist (result record / key)
  (foreach key '(device-library device-overrides)
    (if (assoc key result) (setq record (EL:Put key (EL:Get key result) record)))) record)
(defun EL:DLLegacyInputPaths (panel / path filename paths folder base directories)
  (if (setq path (EL:PowerInputPath panel))
    (progn (setq paths (list path) filename (strcat (vl-filename-base path) ".eld"))
      (if (setq folder (cond (*EL:DLLegacyConfig*)
          ((vl-registry-read "HKEY_CURRENT_USER\\Software\\Emergency-Lighting\\DeviceLibrary" "LegacyConfig"))))
        (setq paths (append paths (list (strcat (EL:NormalizeRoot folder) filename)))))
      (if (setq base (getenv "LOCALAPPDATA"))
        (progn (setq base (strcat (EL:NormalizeRoot base) "Emergency-Lighting/"))
          (setq directories (vl-sort (vl-directory-files base "runtime-*" -1) '(lambda (a b) (> a b))))
          (foreach folder directories
            (setq paths (append paths (list (strcat base folder "/config/" filename)))))))
      (EL:Unique paths))))
(defun EL:DLLegacyInputsWork (panel / paths path data checked found result)
  (setq paths (EL:DLLegacyInputPaths panel))
  (while (and paths (not found))
    (setq path (car paths) paths (cdr paths))
    (if (findfile path)
      (progn (setq found T)
        (if (<= (vl-file-size path) 8388608)
          (setq data (EL:ReadData path) checked (vl-catch-all-apply 'EL:SimplePowersValid (list data))))
        (if (and data (not (vl-catch-all-error-p checked)) checked) (setq result data)
          (EL:DLFail "旧本箱功率缓存损坏或过大，原文件保留；请核对已保存值或重新填写。"))))) result)
(defun EL:DLLegacyInputs (panel / result)
  (setq result (vl-catch-all-apply 'EL:DLLegacyInputsWork (list panel)))
  (if (not (vl-catch-all-error-p result)) result))
(defun EL:DLRestoreRecord (result record)
  (if (or (equal (EL:Get 'engine result) 'fixed) (equal (EL:Get 'engine record) 'fixed)
      (assoc 'device-library result) (assoc 'device-library record))
    (EL:DLRestoreFixedRecord result record) result))
(defun EL:DLRestoreFixedRecord (result record / key row override remembered present)
  (setq present (assoc 'device-overrides result))
  (foreach key '(device-library device-overrides)
    (if (and (not (assoc key result)) (assoc key record)) (setq result (EL:Put key (EL:Get key record) result))))
  ;; A pre-library DWG's saved values are local manual evidence, never global defaults.
  (if (and (not present) (not (assoc 'device-library record)))
    (progn (foreach row (EL:Get 'powers record)
      (setq result (EL:DLSetOverride result (car row) 'watts (cdr row))
        result (EL:DLSetOverride result (car row) 'watts-set T)))
    (foreach row (EL:Get 'block-ground record)
      (setq result (EL:DLSetOverride result (car row) 'is-ground (cdr row))
        result (EL:DLSetOverride result (car row) 'ground-set T)))))
  (if (not present)
    (if (setq remembered (EL:DLLoadInputs (EL:Get 'source-panel-handle record)))
      (foreach row (EL:Get 'device-overrides remembered)
        (setq result (EL:Put 'device-overrides (EL:Put (car row) (cdr row) (EL:Get 'device-overrides result)) result)))
      (if (setq remembered (EL:DLLegacyInputs (EL:Get 'source-panel-handle record)))
        (foreach row (EL:Get 'powers remembered)
          (setq result (EL:DLSetOverride result (car row) 'watts (cdr row))
            result (EL:DLSetOverride result (car row) 'watts-set T)))))) result)
(defun EL:DLSubmissionCurrent (result / snapshot)
  (if (not (assoc 'device-library result)) T
    (progn (setq snapshot (cond (*EL:DLSessionSnapshot*) (T (EL:DLSnapshot))))
      (and snapshot (EL:DLSnapshotCurrent snapshot)))))
(defun EL:DLPanelSubmissionReady (/ snapshot prepared)
  (if (EL:DLSubmissionCurrent *EL:PanelDraft*) T
    (progn
      (if (setq snapshot (EL:DLSnapshotLoad (EL:DLRoot)))
        (progn (setq *EL:DLSessionSnapshot* snapshot *EL:DLCache* nil
          prepared (EL:DLPrepare *EL:PanelDraft* *EL:PanelPowers* snapshot nil)
          *EL:PanelDraft* (EL:Get 'result prepared) *EL:PanelPowers* (EL:Get 'powers prepared)
          *EL:PanelDraft* (EL:PanelCompute *EL:PanelDraft* *EL:PanelPowers* *EL:PanelConfig*))
          (EL:PanelFill)
          (EL:PanelText "p_error" "设备库已变化，库默认值已刷新，手填值保留；请核对后再次保存或生成。"))
        (EL:PanelText "p_error" (cond (*EL:DLError*) (T "设备库无法读取，请修复后重新统计；当前输入保留。")))) nil)))
(defun EL:DLPanelSaveReady (/ snapshot metadata)
  (if (EL:DLSubmissionCurrent *EL:PanelDraft*) T
    (progn
      (setq snapshot (vl-catch-all-apply 'EL:DLSnapshotLoad (list (EL:DLRoot))))
      (if (and (not (vl-catch-all-error-p snapshot)) snapshot)
        (EL:DLPanelSubmissionReady)
        (progn
          ;; Keep exact displayed inputs/references, but prevent diagram generation.
          (setq metadata (EL:Put 'load-error T (EL:Get 'device-library *EL:PanelDraft*))
            *EL:PanelDraft* (EL:PanelCompute (EL:Put 'device-library metadata *EL:PanelDraft*)
              *EL:PanelPowers* *EL:PanelConfig*)) T)))))
(defun EL:DLResumePanel (/ context result)
  (setq context *EL:DLParentContext* *EL:DLParentContext* nil *EL:DLParentContinue* nil
    *EL:DLResume* context *EL:DLSessionSnapshot* nil)
  (if context (progn (EL:PerfStart "ELSTAT") (setq result (EL:EditPanel (EL:Get 'result context) (EL:Get 'config context)))
    (EL:PerfFinish (if result 'returned 'cancelled)))))
(princ)

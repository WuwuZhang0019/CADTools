;; Date: 2026-10-10. WCS device circles/arcs use analytic contact when supported.
;; Other contour callers and unsupported transforms retain bounded sampling.
;; Tilted planes, xrefs and unsupported geometry are diagnosed, never ignored.
(defun EL:PointSegmentDistance (p a b / v w q n)
  (setq v (EL:V- b a) w (EL:V- p a) n (EL:Dot v v))
  (if (< n 1.0e-18) (EL:Norm w)
    (progn (setq q (max 0.0 (min 1.0 (/ (EL:Dot w v) n))))
      (EL:Norm (EL:V- p (EL:V+ a (EL:V* q v)))))))
(defun EL:Touches (p segments tol epsz / hit seg)
  (while (and segments (not hit))
    (setq seg (car segments) segments (cdr segments))
    (if (and (<= (EL:PointSegmentDistance p (car seg) (cadr seg)) tol)
             (<= (abs (- (caddr p) (caddr (car seg)))) epsz)) (setq hit T))) hit)
(defun EL:SegmentsTouchTolerance (a b tol)
  ;; Date: 2026-10-14. XY contact tolerance never merges different elevations.
  (and (<= (abs (- (caddr (car a)) (caddr (car b)))) (EL:GapEpsilon))
    (<= (abs (- (caddr (cadr a)) (caddr (car b)))) (EL:GapEpsilon))
    (<= (abs (- (caddr (cadr b)) (caddr (car b)))) (EL:GapEpsilon))
    (or (EL:Touches (car a) (list b) tol (EL:GapEpsilon))
      (EL:Touches (cadr a) (list b) tol (EL:GapEpsilon))
      (EL:Touches (car b) (list a) tol (EL:GapEpsilon))
      (EL:Touches (cadr b) (list a) tol (EL:GapEpsilon))
      (EL:GapHitsSegment (car a) (cadr a) (car b) (cadr b)))))
(defun EL:PlanarContourTouches (point segments tol / hit seg)
  ;; Date: 2026-10-14. Wider XY tolerance must not accept a sloped device edge
  ;; merely because its first endpoint shares the query point's elevation.
  (while (and segments (not hit))
    (setq seg (car segments) segments (cdr segments))
    (if (and (<= (abs (- (caddr point) (caddr (car seg)))) (EL:GapEpsilon))
        (<= (abs (- (caddr point) (caddr (cadr seg)))) (EL:GapEpsilon))
        (EL:Touches point (list seg) tol (EL:GapEpsilon))) (setq hit T))) hit)
(defun EL:Segments (points / out)
  (while (cdr points)
    (setq out (cons (list (car points) (cadr points)) out) points (cdr points)))
  (reverse out))
(defun EL:AffinePoint (p m)
  (if (not (and (EL:Point p) (= (length m) 8) (not (member nil (mapcar 'numberp m)))))
    (EL:LogEvent "INVALID_AFFINE_INPUT" (list (cons 'point p) (cons 'matrix m))))
  (list (+ (* (nth 0 m) (car p)) (* (nth 2 m) (cadr p)) (nth 4 m))
        (+ (* (nth 1 m) (car p)) (* (nth 3 m) (cadr p)) (nth 5 m))
        (+ (* (nth 7 m) (caddr p)) (nth 6 m))))
(defun EL:AffineCompose (a b / o x y)
  (setq o (EL:AffinePoint (list (nth 4 b) (nth 5 b) (nth 6 b)) a)
        x (EL:AffinePoint (list (+ (nth 4 b) (nth 0 b)) (+ (nth 5 b) (nth 1 b)) (nth 6 b)) a)
        y (EL:AffinePoint (list (+ (nth 4 b) (nth 2 b)) (+ (nth 5 b) (nth 3 b)) (nth 6 b)) a))
  (list (- (car x) (car o)) (- (cadr x) (cadr o))
        (- (car y) (car o)) (- (cadr y) (cadr o)) (car o) (cadr o) (caddr o)
        (* (nth 7 a) (nth 7 b))))
(defun EL:InsertMatrix (e / d p r sx sy sz base o x y b)
  (setq d (entget e) p (cdr (assoc 10 d)) r (cond ((cdr (assoc 50 d))) (T 0.0))
        sx (cond ((cdr (assoc 41 d))) (T 1.0)) sy (cond ((cdr (assoc 42 d))) (T 1.0))
        sz (cond ((cdr (assoc 43 d))) (T 1.0))
        b (tblsearch "BLOCK" (cdr (assoc 2 d))) base (cdr (assoc 10 b)))
  (EL:LogEvent "INSERT_MATRIX_INPUT" (list (EL:LogEntity e) (cons 'block-table b) (cons 'base base) (cons 'scales (list sx sy sz))))
  (setq o (EL:EntityOCSTrans p d nil "INSERT_TRANS" 'origin)
        x (EL:V- (EL:EntityOCSTrans (EL:V+ p (list (* sx (cos r)) (* sx (sin r)) 0.0)) d nil "INSERT_TRANS" 'x-axis) o)
        y (EL:V- (EL:EntityOCSTrans (EL:V+ p (list (* (- sy) (sin r)) (* sy (cos r)) 0.0)) d nil "INSERT_TRANS" 'y-axis) o))
  (setq sz (* sz (caddr (EL:EntityOCSTrans '(0.0 0.0 1.0) d T "INSERT_TRANS" 'z-axis))))
  (if (and (< (abs (caddr x)) 1.0e-9) (< (abs (caddr y)) 1.0e-9))
    (progn
      (setq o (EL:V- o (EL:V+ (EL:V* (car base) x) (EL:V* (cadr base) y))))
      (list (car x) (cadr x) (car y) (cadr y) (car o) (cadr o)
        (- (caddr o) (* sz (caddr base))) sz))))
(defun EL:ArcPoints (center radius start sweep err / n i pts angle)
  (setq n 4)
  (while (and (< n 4096) (> (* radius (- 1.0 (cos (/ (abs sweep) (* 2.0 n))))) err))
    (setq n (* n 2)))
  (if (<= (* radius (- 1.0 (cos (/ (abs sweep) (* 2.0 n))))) err)
    (progn
      (setq i 0)
      (repeat (1+ n)
        (setq angle (+ start (* sweep (/ (float i) n)))
              pts (cons (EL:V+ center (list (* radius (cos angle)) (* radius (sin angle)) 0.0)) pts)
              i (1+ i)))
      (reverse pts))))
(defun EL:BulgePoints (a b bulge err / chord mid left center radius start sweep)
  (if (< (abs bulge) 1.0e-12) (list a b)
    (progn
      (setq chord (EL:V- b a) mid (EL:V* 0.5 (EL:V+ a b))
            left (list (- (cadr chord)) (car chord) 0.0)
            center (EL:V+ mid (EL:V* (/ (- 1.0 (* bulge bulge)) (* 4.0 bulge)) left))
            radius (EL:Norm (EL:V- a center)) start (atan (- (cadr a) (cadr center)) (- (car a) (car center)))
            sweep (* 4.0 (atan bulge)))
      (EL:ArcPoints center radius start sweep err))))
(defun EL:OCSTrans (point normal displacement stage / converted)
  ;; Date: 2026-10-08. Use explicit OCS, including block-definition vertices.
  ;; Parent INSERT matrices are applied later, exactly once by BlockContour.
  (if (not (and (EL:Point point) (EL:Point normal) (> (EL:Norm normal) 1.0e-12)))
    (progn
      (EL:LogEvent (strcat "INVALID_" stage "_INPUT") (list (cons 'point point) (cons 'normal normal)
        (cons 'displacement displacement)))
      (princ "\n对象坐标或法向量无效，已停止识别；请保留诊断日志。")
      (exit)))
  (setq converted (trans point normal 0 displacement))
  (EL:LogEvent (strcat stage "_RESULT") converted)
  (if (not (EL:Point converted))
    (progn
      (EL:LogEvent (strcat "INVALID_" stage "_RESULT") (list (cons 'point point) (cons 'normal normal)
        (cons 'target 0) (cons 'displacement displacement) (cons 'result converted)))
      (princ "\n对象坐标转换未返回有效三维点，已停止识别；请保留诊断日志。")
      (exit)))
  converted)
(defun EL:EntityOCSTrans (point data displacement stage sample / normal)
  (setq normal (cond ((cdr (assoc 210 data))) (T '(0.0 0.0 1.0))))
  (EL:LogCall stage (list (cons 'handle (cdr (assoc 5 data))) (cons 'type (cdr (assoc 0 data)))
    (cons 'point point) (cons 'normal normal) (cons 'target 0) (cons 'displacement displacement)
    (cons 'sample sample) (cons 'method 'extrusion-vector))
    'EL:OCSTrans (list point normal displacement stage)))
(defun EL:PolylineTrans (point normal)
  (EL:OCSTrans point normal nil "POLYLINE_TRANS"))
(defun EL:PolylineData (e)
  (EL:PolylineDataDXF (entget e)))
(defun EL:PolylineDataDXF (data / p elev normal points bulges x converted)
  ;; Date: 2026-10-15. Geometry and diagnostics use the caller's fresh DXF.
  (setq elev (cond ((cdr (assoc 38 data))) (T 0.0))
        normal (cond ((cdr (assoc 210 data))) (T '(0.0 0.0 1.0))))
  (EL:LogEvent "POLYLINE_INPUT" (list (cons 'entity (EL:LogEntityData data)) (cons 'elevation elev) (cons 'raw-dxf data)))
  (foreach x data
    ;; Capture the exact DXF row before numeric group-code comparisons.
    (EL:LogEvent "POLYLINE_DXF_ROW" x)
    (cond ((= (car x) 10)
           (setq p (cdr x)
                 converted (EL:LogCall "POLYLINE_TRANS" (list (cons 'handle (cdr (assoc 5 data)))
                   (cons 'vertex p) (cons 'elevation elev) (cons 'normal normal) (cons 'target 0)
                   (cons 'method 'extrusion-vector))
                   'EL:PolylineTrans (list (list (car p) (cadr p) elev) normal)))
           (setq points (cons converted points)
                 bulges (cons 0.0 bulges)))
          ((= (car x) 42) (setq bulges (cons (cdr x) (cdr bulges))))))
  (EL:LogEvent "POLYLINE_NORMAL" normal)
  (if (< (caddr normal) 0.0)
    (setq bulges (mapcar '- bulges)))
  (list (reverse points) (reverse bulges)))
(defun EL:PolylineSegments (points bulges closed err / out tail bs part)
  (setq tail (if closed (append points (list (car points))) points) bs bulges)
  (while (cdr tail)
    (EL:LogEvent "POLYLINE_SEGMENT" (list (cons 'start (car tail)) (cons 'end (cadr tail))
      (cons 'bulge (car bs)) (cons 'error-bound err)))
    (setq part (EL:BulgePoints (car tail) (cadr tail) (cond ((car bs)) (T 0.0)) err))
    (if part (setq out (append out (EL:Segments part))) (setq out nil tail nil))
    (setq tail (cdr tail) bs (cdr bs))) out)
(defun EL:MakeEnd (id side points bulges layer / p q b rest state direction)
  ;; Last vertex has no outgoing segment: use the penultimate original bulge.
  (if (equal side 'end) (setq points (reverse points) bulges (cdr (reverse bulges))))
  (setq p (car points) rest (cdr points) b (car bulges))
  (while (and rest (< (EL:Norm (EL:V- (car rest) p)) 1.0e-9))
    (setq rest (cdr rest) bulges (cdr bulges) b (car bulges)))
  (setq q (car rest) state (cond ((not q) 'INVALID_GEOMETRY)
      ((and b (> (abs b) 1.0e-12)) 'UNSUPPORTED_END_GEOMETRY) (T 'straight)))
  (if q (setq direction (EL:Unit (EL:V- p q))))
  (list (cons 'key (list id side)) (cons 'wire id) (cons 'side side) (cons 'point p)
        (cons 'direction direction) (cons 'geometry state) (cons 'layer layer)))
;; Date: 2026-10-11. Filled straight polyline widths, with butt ends, in drawing units.
(defun EL:WireWidthProfiles (data points bulges / widths pair current constant variable out)
  (setq constant (cond ((cdr (assoc 43 data))) (T 0.0)))
  (foreach pair data
    (cond ((= (car pair) 10)
           (if current (setq widths (cons current widths))) (setq current '(0.0 0.0)))
          ((and current (= (car pair) 40))
           (setq current (list (cdr pair) (cadr current)) variable T))
          ((and current (= (car pair) 41))
           (setq current (list (car current) (cdr pair)) variable T))))
  (if current (setq widths (reverse (cons current widths))))
  (while (cdr points)
    (setq pair (if variable (car widths) (list constant constant)))
    (if (and pair (>= (car pair) 0.0) (>= (cadr pair) 0.0)
        (> (max (car pair) (cadr pair)) 0.0)
        (or (not (car bulges)) (< (abs (car bulges)) 1.0e-12)))
      (setq out (cons (list (car points) (cadr points) (car pair) (cadr pair)) out)))
    (setq points (cdr points) widths (cdr widths) bulges (cdr bulges)))
  (reverse out))
(defun EL:WireStrip (a b start end / v length normal points ring)
  (setq v (EL:V- b a) length (EL:Norm v))
  (if (and (> length 1.0e-9) (> (max start end) 0.0))
    (progn
      (setq normal (list (/ (- (cadr v)) length) (/ (car v) length) 0.0)
        points (list (EL:V+ a (EL:V* (/ start 2.0) normal))
          (EL:V+ b (EL:V* (/ end 2.0) normal))
          (EL:V- b (EL:V* (/ end 2.0) normal))
          (EL:V- a (EL:V* (/ start 2.0) normal)))
        ring (EL:Segments (append points (list (car points)))))
      (list (cons 'segments ring) (cons 'regions (list ring))))))
(defun EL:WireContactStrips (segments profiles / out segment profile base length start end strip)
  (foreach segment segments
    (foreach profile profiles
      (setq base (list (list (car profile) (cadr profile)))
        length (EL:Norm (EL:V- (cadr profile) (car profile))))
      (if (and (> length 1.0e-9)
          (EL:Touches (car segment) base (EL:GapEpsilon) (EL:GapEpsilon))
          (EL:Touches (cadr segment) base (EL:GapEpsilon) (EL:GapEpsilon)))
        (progn
          (setq start (+ (nth 2 profile) (* (- (nth 3 profile) (nth 2 profile))
            (/ (EL:Norm (EL:V- (car segment) (car profile))) length)))
            end (+ (nth 2 profile) (* (- (nth 3 profile) (nth 2 profile))
            (/ (EL:Norm (EL:V- (cadr segment) (car profile))) length))))
          (if (setq strip (EL:WireStrip (car segment) (cadr segment) start end))
            (setq out (cons strip out)))))))
  (reverse out))
(defun EL:WireContactBounds (wire / segments strip)
  (setq segments (EL:Get 'segments wire))
  (foreach strip (EL:Get 'contact-strips wire)
    (setq segments (append segments (EL:Get 'segments strip))))
  (EL:SegmentBounds segments))
(defun EL:WireRecord (e cfg)
  (EL:WireRecordDXF e (entget e) cfg))
(defun EL:WireRecordDXF (e d cfg / id typ pts bs closed segments ends issues normal total seg bounds profiles)
  ;; Date: 2026-10-15. No second entity read while collecting this wire.
  (setq id (cdr (assoc 5 d)) typ (cdr (assoc 0 d)) normal (cdr (assoc 210 d)))
  (cond ((= typ "LINE") (setq pts (list (cdr (assoc 10 d)) (cdr (assoc 11 d))) bs '(0.0 0.0)))
        ((= typ "LWPOLYLINE")
         (setq pts (EL:PolylineDataDXF d) bs (cadr pts) pts (car pts)
               closed (= (logand 1 (cond ((cdr (assoc 70 d))) (T 0))) 1)))
        (T (setq issues (list (EL:Issue 'UNSUPPORTED_WIRE id typ)))))
  (if (and normal (> (+ (abs (car normal)) (abs (cadr normal))) 1.0e-9))
    (setq issues (cons (EL:Issue 'UNSUPPORTED_PLANE id normal) issues)))
  (if closed (setq issues (cons (EL:Issue 'CLOSED_WIRE id nil) issues)))
  (if pts
    (progn
      (setq segments (EL:PolylineSegments pts bs closed (/ (EL:Get 'eps_boundary (EL:Get 'params cfg)) 8.0)))
      (if (not closed)
        (setq ends (list (EL:MakeEnd id 'start pts bs (cdr (assoc 8 d)))
                         (EL:MakeEnd id 'end pts bs (cdr (assoc 8 d))))))))
  (if (and pts (not segments)) (setq issues (cons (EL:Issue 'INVALID_GEOMETRY id nil) issues)))
  (setq total 0.0)
  (foreach seg segments (setq total (+ total (EL:Norm (EL:V- (cadr seg) (car seg))))))
  (if (and pts (< total 1.0e-9)) (setq issues (cons (EL:Issue 'INVALID_GEOMETRY id nil) issues)))
  (if (and pts (> (- (apply 'max (mapcar 'caddr pts)) (apply 'min (mapcar 'caddr pts))) (EL:Get 'eps_z (EL:Get 'params cfg))))
    (setq issues (cons (EL:Issue 'UNSUPPORTED_PLANE id nil) issues)))
  (if (not (member typ '("LINE" "LWPOLYLINE"))) (setq bounds (EL:LogCall "ENTITY_BOUNDS" (EL:LogEntity e) 'EL:EntityBounds (list e))))
  (if (and (= typ "LWPOLYLINE") (not closed))
    (setq profiles (EL:WireWidthProfiles d pts bs)))
  (list (cons 'id id) (cons 'layer (cdr (assoc 8 d))) (cons 'type typ)
        (cons 'width-profiles profiles) (cons 'contact-strips (EL:WireContactStrips segments profiles))
        (cons 'segments segments) (cons 'bounds bounds) (cons 'ends ends) (cons 'issues issues) (cons 'raw (EL:Signature (EL:CanonicalVisibilityDXF d)))))
(defun EL:TransformSegments (segments matrix)
  (mapcar '(lambda (segment) (list (EL:AffinePoint (car segment) matrix)
    (EL:AffinePoint (cadr segment) matrix))) segments))
(defun EL:CurveSegments (data err / typ center radius start sweep points point converted index)
  (setq typ (cdr (assoc 0 data)) center (cdr (assoc 10 data)) radius (cdr (assoc 40 data))
        start (if (= typ "CIRCLE") 0.0 (cdr (assoc 50 data)))
        sweep (if (= typ "CIRCLE") (* 2.0 pi)
          (rem (+ (* 2.0 pi) (- (cdr (assoc 51 data)) start)) (* 2.0 pi))))
  (setq points (EL:LogCall "CURVE_POINTS" (list (cons 'handle (cdr (assoc 5 data))) (cons 'type typ)
    (cons 'center center) (cons 'radius radius) (cons 'start start) (cons 'sweep sweep) (cons 'error-bound err))
    'EL:ArcPoints (list center radius start sweep err)))
  (EL:LogEvent "CURVE_POINT_COUNT" (list (cons 'handle (cdr (assoc 5 data))) (cons 'count (length points))))
  (setq index 0)
  (foreach point points
    (setq converted (cons (EL:EntityOCSTrans point data nil "CURVE_TRANS" index) converted)
          index (1+ index)))
  (EL:Segments (reverse converted)))
;; Date: 2026-10-10. Analytic primitives: (center radius start signed-sweep hole).
(defun EL:CurvePoint (curve angle)
  (EL:V+ (car curve) (list (* (cadr curve) (cos angle)) (* (cadr curve) (sin angle)) 0.0)))
(defun EL:CurveFull (curve) (>= (abs (nth 3 curve)) (- (* 2.0 pi) 1.0e-12)))
(defun EL:CurveAngleHas (curve point / angle delta)
  (setq angle (atan (- (cadr point) (cadr (car curve))) (- (car point) (caar curve)))
    delta (if (< (nth 3 curve) 0.0) (- (nth 2 curve) angle) (- angle (nth 2 curve)))
    delta (rem (+ (rem delta (* 2.0 pi)) (* 2.0 pi)) (* 2.0 pi)))
  (or (EL:CurveFull curve) (<= delta (+ (abs (nth 3 curve)) (/ (EL:GapEpsilon) (cadr curve))))
    (<= (- (* 2.0 pi) delta) (/ (EL:GapEpsilon) (cadr curve)))))
(defun EL:CurvePointHit (point curve tol)
  (and (<= (abs (- (caddr point) (caddr (car curve)))) (EL:GapEpsilon))
    (or (and (<= (abs (- (EL:Norm (EL:V- point (car curve))) (cadr curve))) tol)
          (EL:CurveAngleHas curve point))
      ;; An open arc has finite endpoints. A nearby angular neighbour is a hit
      ;; only when its Euclidean endpoint distance is within the same tolerance.
      (and (not (EL:CurveFull curve))
        (or (<= (EL:Norm (EL:V- point (EL:CurvePoint curve (nth 2 curve)))) tol)
          (<= (EL:Norm (EL:V- point (EL:CurvePoint curve (+ (nth 2 curve) (nth 3 curve))))) tol))))))
(defun EL:CurveSegmentHit (seg curve tol / a v center len unit along nearest dist delta hit value point)
  (setq a (car seg) v (EL:V- (cadr seg) a) center (car curve) len (EL:Norm v))
  (if (and (<= (abs (- (caddr a) (caddr center))) (EL:GapEpsilon))
           (<= (abs (- (caddr (cadr seg)) (caddr center))) (EL:GapEpsilon)))
    (if (<= len 1.0e-12) (EL:CurvePointHit a curve tol)
      (progn
        (setq unit (EL:V* (/ 1.0 len) v) along (EL:Dot (EL:V- center a) unit)
          nearest (EL:V+ a (EL:V* along unit)) dist (EL:Norm (EL:V- nearest center))
          hit (or (EL:CurvePointHit a curve tol) (EL:CurvePointHit (cadr seg) curve tol)
            (and (not (EL:CurveFull curve))
              (or (<= (EL:PointSegmentDistance (EL:CurvePoint curve (nth 2 curve)) a (cadr seg)) tol)
                (<= (EL:PointSegmentDistance (EL:CurvePoint curve (+ (nth 2 curve) (nth 3 curve))) a (cadr seg)) tol)))))
        (if (<= dist (+ (cadr curve) tol))
          (progn
            (setq delta (sqrt (max 0.0 (* (- (cadr curve) dist) (+ (cadr curve) dist)))))
            (foreach value (list (- along delta) (+ along delta))
              (if (and (>= value (- tol)) (<= value (+ len tol)))
                (progn (setq point (EL:V+ a (EL:V* (max 0.0 (min len value)) unit)))
                  (if (EL:CurvePointHit point curve tol) (setq hit T)))))))
        hit))))
(defun EL:CurvesTouch (a b / delta dist r s x height base normal point hit)
  (setq delta (EL:V- (car b) (car a)) dist (EL:Norm delta) r (cadr a) s (cadr b))
  (if (<= (abs (- (caddr (car a)) (caddr (car b)))) (EL:GapEpsilon))
    (cond
      ((and (<= dist (EL:GapEpsilon)) (<= (abs (- r s)) (EL:GapEpsilon)))
        (or (EL:CurveFull a) (EL:CurveFull b)
          (EL:CurveAngleHas a (EL:CurvePoint b (nth 2 b)))
          (EL:CurveAngleHas a (EL:CurvePoint b (+ (nth 2 b) (nth 3 b))))
          (EL:CurveAngleHas b (EL:CurvePoint a (nth 2 a)))))
      ((and (> dist 1.0e-12) (<= dist (+ r s (EL:GapEpsilon)))
            (>= dist (- (abs (- r s)) (EL:GapEpsilon))))
        (setq x (/ (+ (* (- r s) (+ r s)) (* dist dist)) (* 2.0 dist))
          height (sqrt (max 0.0 (* (- r x) (+ r x))))
          base (EL:V+ (car a) (EL:V* (/ x dist) delta))
          normal (list (/ (- (cadr delta)) dist) (/ (car delta) dist) 0.0))
        (foreach point (list (EL:V+ base (EL:V* height normal)) (EL:V- base (EL:V* height normal)))
          (if (and (EL:CurvePointHit point a (EL:GapEpsilon))
                   (EL:CurvePointHit point b (EL:GapEpsilon))) (setq hit T))) hit))))
(defun EL:CurvesTouchTolerance (a b tol / delta dist unit pa pb sa sb hit)
  ;; Date: 2026-10-14. Keep the original numerical-only primitive unchanged.
  ;; A finite-arc minimum occurs at an endpoint, an actual intersection, or
  ;; two radial points on the line of centres. No expanded circle/AABB is used.
  (if (<= (abs (- (caddr (car a)) (caddr (car b)))) (EL:GapEpsilon))
    (progn
      (setq hit (EL:CurvesTouch a b))
      (if (and (not hit) (> tol (EL:GapEpsilon)))
        (progn
          (foreach pa (list (EL:CurvePoint a (nth 2 a)) (EL:CurvePoint a (+ (nth 2 a) (nth 3 a))))
            (if (EL:CurvePointHit pa b tol) (setq hit T)))
          (foreach pb (list (EL:CurvePoint b (nth 2 b)) (EL:CurvePoint b (+ (nth 2 b) (nth 3 b))))
            (if (EL:CurvePointHit pb a tol) (setq hit T)))
          (setq delta (EL:V- (car b) (car a)) dist (EL:Norm delta))
          (if (> dist 1.0e-12)
            (progn
              (setq unit (EL:V* (/ 1.0 dist) delta))
              (foreach sa '(-1.0 1.0)
                (setq pa (EL:V+ (car a) (EL:V* (* sa (cadr a)) unit)))
                (foreach sb '(-1.0 1.0)
                  (setq pb (EL:V+ (car b) (EL:V* (* sb (cadr b)) unit)))
                  (if (and (EL:CurveAngleHas a pa) (EL:CurveAngleHas b pb)
                      (<= (EL:Norm (EL:V- pa pb)) tol)) (setq hit T))))))))
      hit)))
(defun EL:NativeCurve (data matrix / center x y sx sy start sweep sign)
  (setq center (cdr (assoc 10 data))
    x (EL:AffinePoint (EL:EntityOCSTrans (EL:V+ center '(1.0 0.0 0.0)) data nil "CURVE_FRAME" 'x) matrix)
    y (EL:AffinePoint (EL:EntityOCSTrans (EL:V+ center '(0.0 1.0 0.0)) data nil "CURVE_FRAME" 'y) matrix)
    center (EL:AffinePoint (EL:EntityOCSTrans center data nil "CURVE_FRAME" 'center) matrix)
    x (EL:V- x center) y (EL:V- y center) sx (EL:Norm x) sy (EL:Norm y))
  ;; Similarity only: nonuniform scale/shear uses the existing sampled fallback.
  (if (and (> sx 1.0e-12) (> sy 1.0e-12)
      (<= (abs (- sx sy)) (* 1.0e-10 (min sx sy)))
      (<= (abs (EL:Dot x y)) (* 1.0e-10 sx sy)))
    (progn
      (setq sign (if (< (EL:Cross x y) 0.0) -1.0 1.0)
        start (if (equal (cdr (assoc 0 data)) "CIRCLE") 0.0 (cdr (assoc 50 data)))
        sweep (if (equal (cdr (assoc 0 data)) "CIRCLE") (* 2.0 pi)
          (rem (+ (* 2.0 pi) (- (cdr (assoc 51 data)) start)) (* 2.0 pi))))
      (if (> (cdr (assoc 40 data)) 0.0)
        (list center (* sx (cdr (assoc 40 data))) (+ (atan (cadr x) (car x)) (* sign start))
          (* sign sweep) (equal (strcase (cond ((cdr (assoc 8 data))) (T "0"))) "EL_HOLE"))))))
(defun EL:ShapeGeometry (shape) (or (EL:Get 'segments shape) (EL:Get 'curves shape)))
(defun EL:TranslateCurves (curves offset)
  (mapcar '(lambda (curve) (cons (EL:V+ (car curve) offset) (cdr curve))) curves))
;; Date: 2026-10-13. Reuse definition primitives without sampling circles again.
(defun EL:SimilarityScale (matrix / x y sx sy)
  (setq x (list (nth 0 matrix) (nth 1 matrix) 0.0)
        y (list (nth 2 matrix) (nth 3 matrix) 0.0)
        sx (EL:Norm x) sy (EL:Norm y))
  (if (and (> sx 1.0e-12) (> sy 1.0e-12)
      (<= (abs (- sx sy)) (* 1.0e-10 (min sx sy)))
      (<= (abs (EL:Dot x y)) (* 1.0e-10 sx sy))) sx))
(defun EL:TransformCurve (curve matrix / scale vector start sign)
  (if (setq scale (EL:SimilarityScale matrix))
    (progn
      (setq start (nth 2 curve)
        vector (list (+ (* (nth 0 matrix) (cos start)) (* (nth 2 matrix) (sin start)))
          (+ (* (nth 1 matrix) (cos start)) (* (nth 3 matrix) (sin start))) 0.0)
        sign (if (< (- (* (nth 0 matrix) (nth 3 matrix)) (* (nth 1 matrix) (nth 2 matrix))) 0.0) -1.0 1.0))
      (list (EL:AffinePoint (car curve) matrix) (* scale (cadr curve))
        (atan (cadr vector) (car vector)) (* sign (nth 3 curve)) (nth 4 curve)))))
(defun EL:TransformShape (shape matrix / curves sampled paths holes path)
  (setq curves (EL:Get 'curves shape) sampled (EL:Get 'sampled-curves shape))
  ;; A parent transform can cancel a nested nonuniform scale, making a sampled
  ;; local ellipse an exact WCS circle. Regenerate sampled geometry per instance
  ;; to preserve both its error bound and its analytic/fallback choice.
  (if (and (not sampled) (or (not curves) (EL:SimilarityScale matrix)))
    (progn
      (setq paths (mapcar '(lambda (path) (EL:TransformSegments path matrix)) (EL:Get 'hole-paths shape)))
      ;; Hole closure uses WCS numerical tolerance, after the pose is applied.
      ;; Keep raw paths even when locally open: a smaller pose may close them.
      (if paths
        (foreach path paths (setq holes (append holes (EL:ClosedRings path))))
        (setq holes (mapcar '(lambda (ring) (EL:TransformSegments ring matrix)) (EL:Get 'holes shape))))
      (list (cons 'segments (EL:TransformSegments (EL:Get 'segments shape) matrix))
      (cons 'curves (mapcar '(lambda (curve) (EL:TransformCurve curve matrix)) curves))
      (cons 'regions (mapcar '(lambda (ring) (EL:TransformSegments ring matrix)) (EL:Get 'regions shape)))
      (cons 'holes holes) (cons 'hole-paths paths)
      (cons 'issues (EL:Get 'issues shape)) (cons 'sampled-curves sampled)))))
(defun EL:PolylineCircle (data pd matrix / points bulges center radius start)
  ;; Two closed semicircles with the same winding are an exact full circle.
  ;; PolylineData already applied OCS and reversed bulges for negative normals.
  (setq points (car pd) bulges (cadr pd))
  (if (and (= 1 (logand 1 (cond ((cdr (assoc 70 data))) (T 0))))
      (= (length points) 2) (= (length bulges) 2)
      (= (abs (car bulges)) 1.0)
      (= (car bulges) (cadr bulges))
      (<= (abs (- (caddr (car points)) (caddr (cadr points)))) 1.0e-9))
    (progn
      (setq center (EL:V* 0.5 (EL:V+ (car points) (cadr points)))
        radius (* 0.5 (EL:Norm (EL:V- (car points) (cadr points))))
        start (atan (- (cadr (car points)) (cadr center)) (- (caar points) (car center))))
      (if (> radius 1.0e-12)
        (EL:TransformCurve (list center radius start
          (* (if (< (car bulges) 0.0) -1.0 1.0) 2.0 pi)
          (equal (strcase (cond ((cdr (assoc 8 data))) (T "0"))) "EL_HOLE")) matrix)))))
(defun EL:NativeRegionHit (point curves holes / hit curve)
  (foreach curve curves
    (if (and (EL:CurveFull curve) (equal (not (nth 4 curve)) (not holes))
        (or holes (<= (abs (- (caddr point) (caddr (car curve)))) (EL:GapEpsilon)))
        (< (sqrt (+ (expt (- (car point) (caar curve)) 2) (expt (- (cadr point) (cadr (car curve))) 2))) (cadr curve)))
      (setq hit T))) hit)
(defun EL:CurveNeedsRegionFallback (shape / curves curve other seg point fallback)
  ;; A connected arc can bound a mixed closed region. Preserve that region via
  ;; the established sampler until mixed analytic loop topology is supported.
  (setq curves (EL:Get 'curves shape))
  (foreach curve curves
    (if (not (EL:CurveFull curve))
      (foreach point (list (EL:CurvePoint curve (nth 2 curve)) (EL:CurvePoint curve (+ (nth 2 curve) (nth 3 curve))))
        (foreach seg (EL:Get 'segments shape)
          (if (or (equal point (car seg) 1.0e-7) (equal point (cadr seg) 1.0e-7)) (setq fallback T)))
        (foreach other curves
          (if (and (not (eq curve other)) (EL:CurvePointHit point other (EL:GapEpsilon))) (setq fallback T))))))
  fallback)
(defun EL:DeviceContour (entity / *EL:AnalyticContours* shape)
  (setq *EL:AnalyticContours* T
    shape (EL:BlockContour entity '(1.0 0.0 0.0 1.0 0.0 0.0 0.0 1.0) 0.001 nil))
  (if (EL:CurveNeedsRegionFallback shape)
    (progn (setq *EL:AnalyticContours* nil)
      (EL:LogEvent "ANALYTIC_REGION_FALLBACK" (EL:LogEntity entity))
      (setq shape (EL:BlockContour entity '(1.0 0.0 0.0 1.0 0.0 0.0 0.0 1.0) 0.001 nil))))
  (EL:LogEvent "DEVICE_PRIMITIVES" (list (cons 'lines (length (EL:Get 'segments shape)))
    (cons 'curves (length (EL:Get 'curves shape)))))
  shape)
(defun EL:DeviceDefinitionContour (entity / *EL:AnalyticContours* data matrix shape)
  ;; Date: 2026-10-13. Cache by the actual (including anonymous) definition name.
  ;; Validate the root INSERT plane, but do not include its pose or block base.
  ;; InsertMatrix later maps these definition coordinates to the instance WCS.
  (setq *EL:AnalyticContours* T data (entget entity)
    matrix (EL:InsertMatrix entity)
    shape (EL:BlockDefinitionContour (cdr (assoc 2 data))
      (if matrix '(1.0 0.0 0.0 1.0 0.0 0.0 0.0 1.0)) 0.001 nil))
  (if (EL:CurveNeedsRegionFallback shape)
    (progn (setq *EL:AnalyticContours* nil)
      (EL:LogEvent "ANALYTIC_DEFINITION_REGION_FALLBACK" (EL:LogEntity entity))
      (setq shape (EL:BlockDefinitionContour (cdr (assoc 2 data))
        (if matrix '(1.0 0.0 0.0 1.0 0.0 0.0 0.0 1.0)) 0.001 nil))))
  shape)
;; Date: 2026-10-10. SOLID/TRACE use OCS vertices in perimeter order 10,11,13,12.
(defun EL:SolidSegments (data / points code point)
  (foreach code '(10 11 13 12)
    (if (setq point (cdr (assoc code data)))
      (setq points (append points (list (EL:EntityOCSTrans point data nil "SOLID_TRANS" code))))))
  (setq points (EL:Unique points))
  (if (>= (length points) 3) (EL:Segments (append points (list (car points))))))
(defun EL:BlockContour (e matrix tol stack / d name m)
  (setq d (entget e) name (cdr (assoc 2 d))
        m (EL:LogCall "INSERT_MATRIX" (list (EL:LogEntity e) (cons 'parents stack)) 'EL:InsertMatrix (list e)))
  (EL:LogEvent "BLOCK_CONTOUR_INPUT" (list (cons 'name name) (cons 'matrix m) (cons 'parent-matrix matrix) (cons 'tolerance tol)))
  (EL:BlockDefinitionContour name (if m (EL:AffineCompose matrix m)) tol stack))
(defun EL:BlockDefinitionContour (name matrix tol stack / b child cd typ m result segs issues local pd scale normal holes transformed curves curve regions sampled paths)
  ;; Date: 2026-10-13. Shared traversal for an instance or an unposed definition.
  (setq b (tblsearch "BLOCK" name) m matrix)
  (cond ((or (member name stack) (>= (length stack) 16))
         (setq issues (list (EL:Issue 'RECURSIVE_BLOCK name nil))))
        ((or (not m) (not b) (/= 0 (logand 12 (cond ((cdr (assoc 70 b))) (T 0)))))
         (setq issues (list (EL:Issue 'UNSUPPORTED_BLOCK name 'plane-or-xref))))
        (T
         (setq child (cdr (assoc -2 b))
               scale (max 1.0 (+ (abs (nth 0 m)) (abs (nth 1 m)) (abs (nth 2 m)) (abs (nth 3 m)))))
         (while (and child (/= (cdr (assoc 0 (entget child))) "ENDBLK"))
           (setq cd (entget child) typ (cdr (assoc 0 cd)) local nil normal (cdr (assoc 210 cd)))
           (EL:LogEvent "CONTOUR_ENTITY" (list (cons 'block name) (cons 'parents stack) (EL:LogEntity child) (cons 'matrix m) (cons 'scale scale)))
           (EL:LogEvent "CONTOUR_FILTER_INPUT" (list (cons 'handle (cdr (assoc 5 cd)))
             (cons 'type typ) (cons 'visibility (cdr (assoc 60 cd))) (cons 'normal normal)))
           ;; Code 60 is optional: absent means visible. EQUAL accepts nil.
           (if (not (equal (cdr (assoc 60 cd)) 1))
             (cond
               ((member typ '("TEXT" "MTEXT" "ATTDEF" "ATTRIB" "POINT" "SEQEND")) nil)
               ((and normal (> (+ (abs (car normal)) (abs (cadr normal))) 1.0e-9))
                (setq issues (cons (EL:Issue 'UNSUPPORTED_PLANE name typ) issues)))
               ((= typ "LINE") (setq local (list (list (cdr (assoc 10 cd)) (cdr (assoc 11 cd))))))
               ((member typ '("SOLID" "TRACE"))
                (setq local (EL:SolidSegments cd))
                (if (not local) (setq issues (cons (EL:Issue 'INVALID_CONTOUR name typ) issues))))
               ((= typ "LWPOLYLINE")
                (setq pd (EL:LogCall "POLYLINE_DATA" (EL:LogEntity child) 'EL:PolylineData (list child)))
                (EL:LogEvent "POLYLINE_DATA_RESULT" (list (cons 'data pd) (cons 'flags (cdr (assoc 70 cd)))
                  (cons 'tolerance tol) (cons 'scale scale)))
                (if (and *EL:AnalyticContours* (setq curve (EL:PolylineCircle cd pd m)))
                  (setq curves (cons curve curves))
                  (progn
                    (setq local (EL:LogCall "POLYLINE_SEGMENTS" pd 'EL:PolylineSegments
                      (list (car pd) (cadr pd) (= 1 (logand 1 (cond ((cdr (assoc 70 cd))) (T 0)))) (/ tol (* 8.0 scale)))))
                    (if (vl-some '(lambda (bulge) (> (abs bulge) 1.0e-12)) (cadr pd)) (setq sampled T))
                    (if (not local) (setq issues (cons (EL:Issue 'CONTOUR_RESOLUTION name typ) issues))))))
               ((member typ '("CIRCLE" "ARC"))
                (if (and *EL:AnalyticContours* (setq curve (EL:NativeCurve cd m)))
                  (setq curves (cons curve curves))
                  (progn
                    (setq local (EL:LogCall "CURVE_SEGMENTS" (EL:LogEntity child) 'EL:CurveSegments
                      (list cd (/ tol (* 8.0 scale)))) sampled T)
                    (if (not local) (setq issues (cons (EL:Issue 'CONTOUR_RESOLUTION name nil) issues))))))
               ((= typ "INSERT")
                (setq result (EL:LogCall "NESTED_CONTOUR" (EL:LogEntity child) 'EL:BlockContour (list child m tol (cons name stack)))
                      regions (append regions (EL:Get 'regions result))
                      curves (append curves (EL:Get 'curves result)) holes (append holes (EL:Get 'holes result)) segs (append segs (EL:Get 'segments result)) issues (append issues (EL:Get 'issues result))
                      paths (append paths (EL:Get 'hole-paths result))
                      sampled (or sampled (EL:Get 'sampled-curves result))))
               (T (setq issues (cons (EL:Issue 'UNSUPPORTED_CONTOUR name typ) issues)))))
           (setq transformed (EL:LogCall "CONTOUR_TRANSFORM" (list (cons 'handle (cdr (assoc 5 cd)))
             (cons 'segments local) (cons 'matrix m)) 'EL:TransformSegments (list local m)))
           (EL:LogEvent "CONTOUR_TRANSFORM_RESULT" (list (cons 'handle (cdr (assoc 5 cd))) (cons 'segments transformed)))
           (if (and (equal (strcase (cond ((cdr (assoc 8 cd))) (T "0"))) "EL_HOLE") local)
             (setq paths (cons transformed paths) holes (append holes (EL:ClosedRings transformed))))
           (if (and transformed (member typ '("SOLID" "TRACE")))
             (setq regions (cons transformed regions)))
           (setq segs (append transformed segs))
           (EL:LogEvent "CONTOUR_NEXT" (cdr (assoc 5 cd)))
           (setq child (entnext child)))))
  (if (not (or segs curves)) (setq issues (cons (EL:Issue 'EMPTY_CONTOUR name nil) issues)))
  (list (cons 'segments segs) (cons 'curves curves) (cons 'regions regions) (cons 'holes holes) (cons 'hole-paths paths) (cons 'issues issues)
    (cons 'sampled-curves sampled)))
(defun EL:DynamicState (e / obj props out p)
  (setq obj (vlax-ename->vla-object e))
  (if (= (vla-get-IsDynamicBlock obj) :vlax-true)
    (progn
      (setq props (vlax-invoke obj 'GetDynamicBlockProperties))
      (foreach p props (setq out (cons (list (vla-get-PropertyName p) (vlax-variant-value (vla-get-Value p))) out)))))
  (reverse out))
(defun EL:DefinitionData (name stack / b e rows d)
  (if (not (member name stack))
    (progn
      (setq b (tblsearch "BLOCK" name) e (cdr (assoc -2 b)))
      (while (and e (/= (cdr (assoc 0 (entget e))) "ENDBLK"))
        (setq d (vl-remove-if '(lambda (row) (member (car row) '(-1 5 330))) (entget e)))
        (if (= (cdr (assoc 0 d)) "INSERT")
          (setq rows (cons (EL:DefinitionData (cdr (assoc 2 d)) (cons name stack)) rows)))
        (setq rows (cons d rows) e (entnext e)))
      (list (cdr (assoc 10 b)) (reverse rows)))))
(defun EL:EntityBounds (e / lo hi result)
  (setq result (vl-catch-all-apply 'vla-GetBoundingBox (list (vlax-ename->vla-object e) 'lo 'hi)))
  (if (not (vl-catch-all-error-p result)) (list (vlax-safearray->list lo) (vlax-safearray->list hi))))
(defun EL:InBounds (point bounds tolerance)
  (and bounds (>= (car point) (- (car (car bounds)) tolerance)) (<= (car point) (+ (car (cadr bounds)) tolerance))
    (>= (cadr point) (- (cadr (car bounds)) tolerance)) (<= (cadr point) (+ (cadr (cadr bounds)) tolerance))
    (>= (caddr point) (- (caddr (car bounds)) tolerance)) (<= (caddr point) (+ (caddr (cadr bounds)) tolerance))))
(defun EL:BoundsSegments (bounds / a b z)
  (if bounds
    (progn (setq a (car bounds) b (cadr bounds) z (caddr a))
      (EL:Segments (list (list (car a) (cadr a) z) (list (car b) (cadr a) z)
        (list (car b) (cadr b) z) (list (car a) (cadr b) z) (list (car a) (cadr a) z))))))
(defun EL:SegmentBounds (segments / xmin ymin zmin xmax ymax zmax seg point x y z count)
  ;; Date: 2026-10-10. Scalar extrema avoid two temporary lists per endpoint.
  (setq count 0)
  (foreach seg segments
    (foreach point seg
      (setq x (car point) y (cadr point) z (caddr point))
      (if xmin
        (setq xmin (min xmin x) ymin (min ymin y) zmin (min zmin z)
              xmax (max xmax x) ymax (max ymax y) zmax (max zmax z))
        (setq xmin x ymin y zmin z xmax x ymax y zmax z)))
    (setq count (1+ count))
    (if (and *EL:ContactContext* (= (rem count 4096) 0))
      (EL:ContactProgress "bounds" count *EL:ContactContext*)))
  (if xmin (list (list xmin ymin zmin) (list xmax ymax zmax))))
(defun EL:ContactProgress (phase completed context)
  (if *EL:LogActive*
    (progn
      (EL:LogEvent "CONTACT_PROGRESS" (list (cons 'phase phase) (cons 'completed completed) (cons 'object context)))
      (vl-catch-all-apply 'grtext (list -1 (strcat "设备轮廓 "
        (cond ((EL:Get 'id context)) (T "未知")) " / " (cond ((equal phase "read") "读取图块") ((equal phase "bounds") "计算范围")
          ((equal phase "prepare") "准备接触检查") ((equal phase "ready") "准备完成") (T phase)) " / " (itoa completed)))))))
;; Contour order retains local adjacency. Balanced construction consumes each
;; item once, without sorting or copying sublists at every recursive level.
(defun EL:ContourTree (items / *EL:ContourCursor*)
  (setq *EL:ContourCursor* items)
  (EL:ContourTreeTake (length items)))
(defun EL:ContourTreeTake (count / mid left right pivot bounds lo hi child)
  (if (> count 0)
    (progn
      (setq mid (/ count 2) left (EL:ContourTreeTake mid)
            pivot (car *EL:ContourCursor*) *EL:ContourCursor* (cdr *EL:ContourCursor*)
            right (EL:ContourTreeTake (- count mid 1))
            bounds (EL:Get 'bounds pivot) lo (car bounds) hi (cadr bounds))
      (foreach child (list left right)
        (if child (setq lo (mapcar 'min lo (nth 3 child)) hi (mapcar 'max hi (nth 4 child)))))
      (list pivot left right lo hi))))
(defun EL:BoundsOverlap (a b tol)
  (and a b (<= (caar a) (+ (car (cadr b)) tol)) (>= (car (cadr a)) (- (caar b) tol))
    (<= (cadr (car a)) (+ (cadr (cadr b)) tol)) (>= (cadr (cadr a)) (- (cadr (car b)) tol))
    (<= (caddr (car a)) (+ (caddr (cadr b)) tol)) (>= (caddr (cadr a)) (- (caddr (car b)) tol))))
(defun EL:SpatialBoxQuery (tree bounds tol / item result)
  (if (and tree (EL:BoundsOverlap (list (nth 3 tree) (nth 4 tree)) bounds tol))
    (progn
      (setq item (car tree))
      (if (EL:BoundsOverlap (EL:Get 'bounds item) bounds tol) (setq result (list item)))
      (append result (EL:SpatialBoxQuery (cadr tree) bounds tol)
                     (EL:SpatialBoxQuery (caddr tree) bounds tol)))))
(defun EL:RingItems (segments / items seg a b index)
  ;; Date: 2026-10-08. XY broad phase only; exact 3D endpoint tests follow.
  (setq index 0)
  (foreach seg segments
    (setq a (list (caar seg) (cadr (car seg)) 0.0)
          b (list (car (cadr seg)) (cadr (cadr seg)) 0.0)
          items (cons (list (cons 'key index) (cons 'segment seg)
            (cons 'point (EL:V* 0.5 (EL:V+ a b)))
            (cons 'bounds (list (mapcar 'min a b) (mapcar 'max a b)))) items)
          index (1+ index)))
  (reverse items))
(defun EL:RingUsed (marks index size / mid)
  ;; Persistent balanced bit tree: no linear MEMBER/VL-REMOVE per edge.
  (if marks
    (if (= size 1) T
      (progn (setq mid (/ size 2))
        (if (< index mid) (EL:RingUsed (car marks) index mid)
          (EL:RingUsed (cadr marks) (- index mid) (- size mid)))))))
(defun EL:RingMark (marks index size / mid)
  (if (= size 1) T
    (progn (setq mid (/ size 2))
      (if (< index mid)
        (list (EL:RingMark (car marks) index mid) (cadr marks))
        (list (car marks) (EL:RingMark (cadr marks) (- index mid) (- size mid)))))))
(defun EL:RegionProgress (phase completed total)
  (EL:LogEvent "REGION_PROGRESS" (list (cons 'phase phase) (cons 'completed completed) (cons 'total total)))
  (if *EL:LogActive*
    (vl-catch-all-apply 'grtext (list -1 (strcat "闭合区域检查 " phase " " (itoa completed) "/" (itoa total)))))
  nil)
(defun EL:ClosedRings (segments / items tree marks count done item candidate ring start point query matches seg loops finished)
  ;; Only unbranched closed paths define interiors. Keep original input order.
  (setq count (length segments) done 0 items (EL:RingItems segments))
  (EL:RegionProgress "index" 0 count)
  (setq tree (EL:ContourTree items))
  (foreach item items
    (if (not (EL:RingUsed marks (EL:Get 'key item) count))
      (progn
        (setq seg (EL:Get 'segment item) marks (EL:RingMark marks (EL:Get 'key item) count)
              done (1+ done) ring (list seg) start (car seg) point (cadr seg) finished nil)
        (while (and (not finished) (not (equal start point 1.0e-7)))
          (setq query (list (car point) (cadr point) 0.0) matches nil)
          (foreach candidate (EL:SpatialBoxQuery tree (list query query) 1.0e-7)
            (setq seg (EL:Get 'segment candidate))
            (if (and (not (EL:RingUsed marks (EL:Get 'key candidate) count))
                (or (equal point (car seg) 1.0e-7) (equal point (cadr seg) 1.0e-7)))
              (setq matches (cons candidate matches))))
          (if (= (length matches) 1)
            (progn
              (setq candidate (car matches) seg (EL:Get 'segment candidate)
                    marks (EL:RingMark marks (EL:Get 'key candidate) count) done (1+ done))
              (if (equal point (cadr seg) 1.0e-7) (setq seg (reverse seg)))
              (setq ring (cons seg ring) point (cadr seg)))
            (setq finished T))
          (if (= (rem done 256) 0) (EL:RegionProgress "link" done count)))
        (setq ring (reverse ring))
        (if (and (not finished) (> (length ring) 2) (EL:SimpleRing ring)) (setq loops (cons ring loops))))))
  (EL:LogEvent "REGION_RESULT" (list (cons 'segments count) (cons 'rings (length loops))))
  (EL:RegionProgress "done" done count)
  loops)
(defun EL:SimpleRing (ring / valid a b elevation items tree item candidates candidate checked total)
  (setq valid T elevation (caddr (caar ring)) checked 0 total (length ring))
  (foreach a ring
    (if (or (> (abs (- (caddr (car a)) elevation)) (EL:GapEpsilon))
            (> (abs (- (caddr (cadr a)) elevation)) (EL:GapEpsilon))) (setq valid nil)))
  (if valid
    (progn
      (setq items (EL:RingItems ring) tree (EL:ContourTree items))
      (while (and valid items)
        (setq item (car items) a (EL:Get 'segment item)
              candidates (EL:SpatialBoxQuery tree (EL:Get 'bounds item) (EL:GapEpsilon)))
        (while (and valid candidates)
          (setq candidate (car candidates) b (EL:Get 'segment candidate))
          ;; Check both directions once: endpoint-to-interior hits are asymmetric.
          (if (and (< (EL:Get 'key item) (EL:Get 'key candidate)) (not (equal a b))
              (or (EL:GapHitsSegment (car a) (cadr a) (car b) (cadr b))
                  (EL:GapHitsSegment (car b) (cadr b) (car a) (cadr a))))
            (setq valid nil))
          (setq candidates (cdr candidates)))
        (setq items (cdr items) checked (1+ checked))
        (if (= (rem checked 256) 0) (EL:RegionProgress "intersections" checked total)))))
  valid)
(defun EL:AmbiguousRings (rings holes / ambiguous a b)
  (foreach a rings
    (foreach b rings
      (if (and (not (equal a b)) (not (vl-some '(lambda (h) (equal (EL:SegmentBounds a) (EL:SegmentBounds h))) holes))
               (EL:InsideSegments (caar a) b)) (setq ambiguous T))))
  ambiguous)
(defun EL:XYBounds (bounds)
  (if bounds (list (list (caar bounds) (cadr (car bounds)) 0.0)
    (list (car (cadr bounds)) (cadr (cadr bounds)) 0.0))))
(defun EL:ContactRings (rings / rows ring)
  (foreach ring rings (setq rows (cons (list ring (EL:XYBounds (EL:SegmentBounds ring))) rows)))
  (reverse rows))
(defun EL:PrepareContourContact (block / segments bounds tree count *EL:ContactContext*)
  ;; Date: 2026-10-10. Keep object identity/count in every expensive stage.
  (setq segments (EL:Get 'segments block) count (length segments)
        *EL:ContactContext* (list (cons 'id (EL:Get 'id block)) (cons 'name (EL:Get 'name block)) (cons 'segments count)))
  (EL:ContactProgress "prepare" 0 *EL:ContactContext*)
  (if (and *EL:LogActive* (>= count 4096))
    (princ (strcat "\n正在检查设备 " (cond ((EL:Get 'id block)) (T "未知"))
      "，轮廓 " (itoa count) " 段；可按 Esc 取消。")))
  ;; Native INSERT extents are conservative broad-phase bounds only.
  ;; Exact contact still tests sampled segments, closed rings and holes.
  (setq bounds (cond ((EL:Get 'contact-envelope block)) ((EL:Get 'segment-bounds block))
    (T (EL:LogCall "CONTACT_BOUNDS" *EL:ContactContext* 'EL:SegmentBounds (list segments)))))
  (if (>= count 64) (setq tree (EL:LogCall "CONTACT_TREE" *EL:ContactContext* 'EL:ContourTree (list (EL:RingItems segments)))))
  (EL:ContactProgress "ready" count *EL:ContactContext*)
  (append block (list (cons 'segment-bounds bounds) (cons 'contact-ready T) (cons 'contact-segment-bounds (EL:XYBounds bounds))
    (cons 'contact-path-bounds (cond ((EL:Get 'bounds block)) (T bounds)))
    (cons 'contact-tree tree) (cons 'contact-regions (EL:ContactRings (EL:Get 'regions block)))
    (cons 'contact-holes (EL:ContactRings (EL:Get 'holes block))))))
(defun EL:PrepareContactBlock (block)
  (if (EL:Get 'whole-block block)
    (append block (list (cons 'contact-path-bounds (EL:Get 'bounds block))))
    (EL:PrepareContourContact block)))
(defun EL:ContactSegments (block bounds)
  (EL:ContactSegmentsTolerance block bounds (EL:GapEpsilon)))
(defun EL:ContactSegmentsTolerance (block bounds tol / template offset matrix)
  ;; Date: 2026-10-10. Query the shared index before translating selected edges.
  (if (setq template (EL:Get 'contact-template block))
    (progn
      (setq offset (EL:Get 'contact-offset block)
        matrix (list 1.0 0.0 0.0 1.0 (car offset) (cadr offset) (caddr offset) 1.0))
      (EL:TransformSegments (EL:ContactSegmentsTolerance template
        (mapcar '(lambda (point) (EL:V- point offset)) bounds) tol) matrix))
    (EL:ContactSegmentsDirectTolerance block bounds tol)))
(defun EL:ContactSegmentsDirect (block bounds)
  (EL:ContactSegmentsDirectTolerance block bounds (EL:GapEpsilon)))
(defun EL:ContactSegmentsDirectTolerance (block bounds tol / tree)
  (if (EL:Get 'contact-ready block)
    (if (EL:BoundsOverlap (EL:XYBounds bounds) (EL:Get 'contact-segment-bounds block) tol)
      (if (setq tree (EL:Get 'contact-tree block))
        (mapcar '(lambda (row) (EL:Get 'segment row)) (EL:SpatialBoxQuery tree (EL:XYBounds bounds) tol))
        (EL:Get 'segments block)))
    (EL:Get 'segments block)))
(defun EL:PointContactBounds (point tol)
  (list (list (- (car point) tol) (- (cadr point) tol) 0.0)
        (list (+ (car point) tol) (+ (cadr point) tol) 0.0)))
(defun EL:ContourContains (point block)
  ;; Date: 2026-10-10. Reuse prepared regions and holes in template coordinates.
  (if (EL:Get 'contact-template block)
    (EL:ContourContainsDirect (EL:V- point (EL:Get 'contact-offset block)) (EL:Get 'contact-template block))
    (EL:ContourContainsDirect point block)))
(defun EL:ContourContainsDirect (point block / hit loop holes rows row bounds)
  (setq rows (if (EL:Get 'contact-ready block) (EL:Get 'contact-regions block)
    (mapcar '(lambda (ring) (list ring nil)) (EL:Get 'regions block))))
  (while (and rows (not hit))
    (setq row (car rows) loop (car row) bounds (cadr row) rows (cdr rows))
    (if (and (or (not bounds) (EL:BoundsOverlap (EL:PointContactBounds point 0.0) bounds 0.0))
             (<= (abs (- (caddr point) (caddr (caar loop)))) (EL:GapEpsilon))
             (EL:InsideSegments point loop)) (setq hit T)))
  (if (or hit (EL:NativeRegionHit point (EL:Get 'curves block) nil))
    (progn
      (setq rows (if (EL:Get 'contact-ready block) (EL:Get 'contact-holes block)
        (mapcar '(lambda (ring) (list ring nil)) (EL:Get 'holes block))))
      (while (and rows (not holes))
        (setq row (car rows) loop (car row) bounds (cadr row) rows (cdr rows))
        ;; Hole subtraction keeps the existing XY-only semantics.
        (if (and (or (not bounds) (EL:BoundsOverlap (EL:PointContactBounds point 0.0) bounds 0.0))
                 (EL:InsideSegments point loop)) (setq holes T)))))
  (and (or hit (EL:NativeRegionHit point (EL:Get 'curves block) nil))
    (not holes) (not (EL:NativeRegionHit point (EL:Get 'curves block) T))))
(defun EL:RegionContains (point block)
  (if (EL:Get 'whole-block block) (EL:InBounds point (EL:Get 'bounds block) (EL:GapEpsilon))
    (EL:ContourContains point block)))
(defun EL:ContourPointHit (point block cfg)
  (if (EL:Get 'contact-template block)
    (EL:ContourPointHit (EL:V- point (EL:Get 'contact-offset block)) (EL:Get 'contact-template block) cfg)
    (or (vl-some '(lambda (curve) (EL:CurvePointHit point curve (EL:Get 'eps_boundary (EL:Get 'params cfg)))) (EL:Get 'curves block))
      (EL:ContourPointHitLinear point block cfg))))
(defun EL:ContourPointHitLinear (point block cfg)
  (or (EL:PlanarContourTouches point (EL:ContactSegments block
        (EL:PointContactBounds point (EL:Get 'eps_boundary (EL:Get 'params cfg))))
        (EL:Get 'eps_boundary (EL:Get 'params cfg)))
      (EL:RegionContains point block)))
(defun EL:BlockPointHit (point block cfg)
  (if (EL:Get 'whole-block block)
    (EL:InBounds point (EL:ExpandedBlockBounds (EL:Get 'bounds block)
      (EL:Get 'eps_boundary (EL:Get 'params cfg))) (EL:GapEpsilon))
    (EL:ContourPointHit point block cfg)))
(defun EL:PathBlockHit (wire block cfg)
  (if (EL:Get 'whole-block block) (EL:WholePathHit wire block cfg)
    (EL:ContourPathHit wire block cfg)))
(defun EL:ContourPathHit (wire block cfg / hit seg edge segments candidates)
  (setq segments (EL:Get 'segments wire))
  (while (and segments (not hit))
    (setq seg (car segments) segments (cdr segments))
    (if (or (EL:BlockPointHit (car seg) block cfg) (EL:BlockPointHit (cadr seg) block cfg)
            (EL:RegionContains (EL:V* 0.5 (EL:V+ (car seg) (cadr seg))) block)) (setq hit T))
    (if (not hit)
      (setq hit (vl-some '(lambda (curve) (EL:CurveSegmentHit seg curve (EL:Get 'eps_boundary (EL:Get 'params cfg))))
        (EL:Get 'curves block))))
    (if (not hit) (setq candidates (EL:ContactSegmentsTolerance block (EL:SegmentBounds (list seg))
      (EL:Get 'eps_boundary (EL:Get 'params cfg)))))
    (while (and candidates (not hit))
      (setq edge (car candidates) candidates (cdr candidates))
      (if (EL:SegmentsTouchTolerance seg edge (EL:Get 'eps_boundary (EL:Get 'params cfg))) (setq hit T))))
  hit)
(defun EL:BlockRecord (e cfg / d name identity role bounds segments issues)
  ;; Date: 2026-10-08. Treat INSERT as one WCS box; never traverse its contents.
  (setq d (entget e) name (EL:LogCall "EFFECTIVE_NAME" (EL:LogEntity e) 'EL:EffectiveName (list e))
        identity (list name (EL:LogCall "DYNAMIC_STATE" (EL:LogEntity e) 'EL:DynamicState (list e))
          (EL:Signature (list 'whole-block-v1 (EL:DrawingID) (cdr (assoc 2 d)))))
        role (cond ((EL:Get 'role (EL:By 'identity identity (EL:Get 'roles cfg))))
                   ((EL:Get 'role (EL:By 'identity identity *EL:LibraryRoles*))))
        bounds (EL:LogCall "BLOCK_BOUNDS" (EL:LogEntity e) 'EL:EntityBounds (list e)))
  (if (not bounds) (setq issues (list (EL:Issue 'MISSING_BLOCK_BOUNDS (cdr (assoc 5 d)) nil))))
  (setq segments (EL:BoundsSegments bounds))
  (list (cons 'id (cdr (assoc 5 d))) (cons 'layer (cdr (assoc 8 d))) (cons 'name name)
        (cons 'role (cond (role) (T (EL:Role (cdr (assoc 8 d)) name cfg))))
        (cons 'identity identity) (cons 'whole-block T)
        (cons 'regions (if segments (list segments))) (cons 'holes nil)
        (cons 'segments segments) (cons 'issues issues) (cons 'bounds bounds)
        (cons 'raw (EL:Signature (list d identity bounds)))))
(defun EL:ExpandedBlockBounds (bounds tol)
  (if bounds (list (EL:V- (car bounds) (list tol tol 0.0))
                  (EL:V+ (cadr bounds) (list tol tol 0.0)))))
(defun EL:SegmentBoxHit (segment bounds tol / expanded)
  (setq expanded (EL:ExpandedBlockBounds bounds tol))
  (and expanded (EL:RayBoxHits (car segment) (EL:V- (cadr segment) (car segment))
    1.0 (car expanded) (cadr expanded))))
(defun EL:WholePathHit (wire block cfg / segments hit)
  (setq segments (EL:Get 'segments wire))
  (while (and segments (not hit))
    (setq hit (EL:SegmentBoxHit (car segments) (EL:Get 'bounds block)
      (EL:Get 'eps_boundary (EL:Get 'params cfg))) segments (cdr segments)))
  hit)
(defun EL:CollectEndpointSnapshot (cfg / ss i e d layer wires blocks ends issues rec data inserts bounds tree candidate candidates tol outside *EL:LibraryRoles* started collected parsed)
  (setq started (EL:Tick) *EL:LibraryRoles* (if *EL:Root* (EL:LoadRoleLibrary)))
  (setq ss (ssget "_X" '((410 . "Model"))) i 0 tol (EL:Get 'eps_boundary (EL:Get 'params cfg)))
  (if ss
    (repeat (sslength ss)
      (setq e (ssname ss i) d (entget e) layer (cdr (assoc 8 d)) i (1+ i))
      (if *EL:GapStage* (setq *EL:GapStage* (strcat "采集对象 " (vl-prin1-to-string (cdr (assoc 5 d))) "；类型 " (vl-prin1-to-string (cdr (assoc 0 d))))))
      (if (not (EL:ManagedEntity e)) (progn
      (cond
        ((equal (cdr (assoc 0 d)) "INSERT")
          (setq bounds (EL:EntityBounds e))
          ;; Missing COM bounds is conservative: parse, never discard the object.
          (if bounds (setq inserts (cons (list (cons 'key (cdr (assoc 5 d))) (cons 'point (EL:V* 0.5 (EL:V+ (car bounds) (cadr bounds)))) (cons 'entity e) (cons 'bounds bounds)) inserts))
            (setq candidates (cons e candidates))))
        ((member layer (EL:Get 'wire-layers cfg))
          (setq rec (EL:LogCall "WIRE_RECORD" (EL:LogEntity e) 'EL:WireRecord (list e cfg)) wires (cons rec wires) ends (append ends (EL:Get 'ends rec))))
        ((member (cdr (assoc 0 d)) '("LINE" "LWPOLYLINE"))
          (setq outside (cons (EL:LogCall "OUTSIDE_WIRE_RECORD" (EL:LogEntity e) 'EL:WireRecord (list e cfg)) outside))))
      (setq data (cons (list (cdr (assoc 5 d)) d) data))))))
  (setq collected (EL:Elapsed started) parsed (EL:Tick) tree (EL:LogCall "BLOCK_INDEX" (list (cons 'count (length inserts))) 'EL:SpatialTree (list inserts 0)))
  (foreach rec wires
    (foreach candidate (EL:SpatialBoxQuery tree (EL:SegmentBounds (EL:Get 'segments rec)) tol)
      (setq candidates (cons (EL:Get 'entity candidate) candidates))))
  (foreach e (EL:Unique candidates)
    (setq rec (EL:LogCall "CANDIDATE_BLOCK" (EL:LogEntity e) 'EL:BlockRecord (list e cfg)) blocks (cons rec blocks)
          data (cons (list (EL:Get 'id rec) (EL:Get 'raw rec)) data)))
  (foreach rec (append wires blocks) (setq issues (append issues (EL:Get 'issues rec))))
  (EL:LogEvent "SNAPSHOT_COUNTS" (list (cons 'wires (length wires)) (cons 'blocks (length blocks)) (cons 'ends (length ends)) (cons 'issues issues)))
  (setq data (vl-sort data '(lambda (a b) (< (EL:Signature a) (EL:Signature b)))))
  (list (cons 'drawing (EL:DrawingID)) (cons 'wires wires) (cons 'blocks blocks) (cons 'outside-wires outside)
        (cons 'timing (list (cons 'collection-ms collected) (cons 'contours-ms (EL:Elapsed parsed))
          (cons 'wire-count (length wires)) (cons 'parsed-block-count (length blocks))))
        (cons 'ends ends) (cons 'issues issues) (cons 'signature (EL:Signature (list data *EL:LibraryRoles*)))))
(defun EL:GapHitsSegment (p q a b / v w den tval uval)
  (setq v (EL:V- q p) w (EL:V- b a) den (EL:Cross v w))
  (if (> (abs den) 1.0e-12)
    (progn
      (setq tval (/ (EL:Cross (EL:V- a p) w) (float den)) uval (/ (EL:Cross (EL:V- a p) v) (float den)))
      (and (> tval 1.0e-9) (< tval (- 1.0 1.0e-9)) (>= uval 0.0) (<= uval 1.0)))))
 ;; Only numerical roundoff, not a drawing/alignment tolerance (mm).
(defun EL:GapEpsilon () 1.0e-7)
(defun EL:GapEligible (end)
  (and (not (EL:Get 'occupied end)) (not (EL:Get 'wire-attached end))
       (equal (EL:Get 'geometry end) 'straight) (EL:Get 'direction end)))
(defun EL:SpatialTree (items axis / keyed item invalid)
  ;; Date: 2026-10-13. Compute stable tie-break keys once per item, not once
  ;; per sort comparison at every tree level (planar drawings share Z=0).
  (if *EL:LogActive*
    (progn
      (setq invalid (vl-remove-if '(lambda (row) (EL:Point (EL:Get 'point row))) items))
      (if invalid (EL:LogEvent "INDEX_INVALID_POINTS" (list axis invalid)))))
  (foreach item items
    ;; Date: 2026-10-15. Keep coordinates beside the tie-break key; native
    ;; list access replaces repeated alist searches inside sort comparisons.
    (setq keyed (cons (cons (EL:Get 'point item) (cons (EL:Signature (EL:Get 'key item)) item)) keyed)))
  (EL:SpatialTreeBuild (reverse keyed) axis))
(defun EL:SpatialTreeBuild (items axis / sorted mid item pivot left right lo hi bounds)
  ;; Preserve the existing axis order, tie-break order and public tree layout.
  (if items
    (progn
      (if (not (cdr items))
        (setq pivot (cddr (car items)))
        (progn
          (setq sorted (vl-sort items '(lambda (a b)
            (if (= (nth axis (car a)) (nth axis (car b)))
              (< (cadr a) (cadr b))
              (< (nth axis (car a)) (nth axis (car b))))))
            mid (/ (length sorted) 2))
          ;; Date: 2026-10-15. Consume only the left half in Lisp; native
          ;; REVERSE preserves the original right-half order before sorting.
          (repeat mid (setq left (cons (car sorted) left) sorted (cdr sorted)))
          (setq pivot (cddr (car sorted)) right (reverse (cdr sorted)))
          (setq left (EL:SpatialTreeBuild left (fix (rem (1+ axis) 3)))
            right (EL:SpatialTreeBuild right (fix (rem (1+ axis) 3))))))
      (setq bounds (EL:Get 'bounds pivot)
            lo (if bounds (car bounds) (EL:Get 'point pivot))
            hi (if bounds (cadr bounds) lo))
      (foreach item (list left right)
        (if item (setq lo (mapcar 'min lo (nth 3 item)) hi (mapcar 'max hi (nth 4 item)))))
      (list pivot left right lo hi))))
(defun EL:RayBoxHits (p direction limit lo hi / axis low high d near far tmp ok eps)
  (setq axis 0 near 0.0 far limit ok T eps (EL:GapEpsilon))
  ;; Date: 2026-10-15. A rejected slab cannot be recovered by later axes.
  ;; Retain the exact subtraction/division order and epsilon on visited axes.
  (while (and ok (< axis 3))
    (setq low (- (nth axis lo) eps (nth axis p))
          high (- (+ (nth axis hi) eps) (nth axis p)) d (nth axis direction))
    (if (< (abs d) 1.0e-15)
      (if (or (> low 0.0) (< high 0.0)) (setq ok nil))
      (progn
        (setq low (/ low d) high (/ high d))
        (if (> low high) (setq tmp low low high high tmp))
        (setq near (max near low) far (min far high))
        (if (> near far) (setq ok nil))))
    (setq axis (1+ axis))) ok)
(defun EL:SpatialRayQuery (tree p direction limit / item bounds result)
  (if (and tree (EL:RayBoxHits p direction limit (nth 3 tree) (nth 4 tree)))
    (progn
      (setq item (car tree) bounds (EL:Get 'bounds item))
      (if (EL:RayBoxHits p direction limit
            (if bounds (car bounds) (EL:Get 'point item))
            (if bounds (cadr bounds) (EL:Get 'point item))) (setq result (list item)))
      (append result (EL:SpatialRayQuery (cadr tree) p direction limit)
                     (EL:SpatialRayQuery (caddr tree) p direction limit)))))
(defun EL:GapPathIndex (snapshot / items item seg)
  (foreach item (append (EL:Get 'wires snapshot) (EL:Get 'blocks snapshot))
    (if (EL:Get 'whole-block item)
      (if (and (EL:Get 'bounds item) (not (equal (EL:Get 'role item) 'ignore)))
        (setq items (cons (list (cons 'key (EL:Get 'id item)) (cons 'id (EL:Get 'id item))
          (cons 'whole-block T) (cons 'bounds (EL:Get 'bounds item))
          (cons 'point (EL:V* 0.5 (EL:V+ (car (EL:Get 'bounds item)) (cadr (EL:Get 'bounds item)))))) items)))
      (foreach seg (EL:Get 'segments item)
      (setq items (cons (list (cons 'key (list (EL:Get 'id item) seg)) (cons 'id (EL:Get 'id item))
        (cons 'point (EL:V* 0.5 (EL:V+ (car seg) (cadr seg)))) (cons 'segment seg)
        (cons 'bounds (list (mapcar 'min (car seg) (cadr seg)) (mapcar 'max (car seg) (cadr seg))))) items)))))
  (EL:SpatialTree items 0))
(defun EL:GapBlocked (a b snapshot params / p q tdir len blocked item seg lo hi eps tree)
  ;; Non-collinear wires do not block; whole equipment boxes do.
  (setq p (EL:Get 'point a) q (EL:Get 'point b) tdir (EL:Unit (EL:V- q p))
        len (EL:Norm (EL:V- q p)) eps (EL:GapEpsilon)
        tree (if *EL:GapIndexReady* *EL:GapPathIndex* (EL:GapPathIndex snapshot)))
  (foreach item (EL:SpatialRayQuery tree p tdir len)
    (setq seg (EL:Get 'segment item))
    (if (EL:Get 'whole-block item)
      (if (EL:SegmentBoxHit (list p q) (EL:Get 'bounds item) 0.0)
        (setq blocked (cons (EL:Get 'id item) blocked)))
    (if (and (<= (abs (- (caddr (car seg)) (caddr p))) eps)
             (<= (abs (- (caddr (cadr seg)) (caddr p))) eps)
             (<= (abs (EL:Cross (EL:V- (car seg) p) tdir)) eps)
             (<= (abs (EL:Cross (EL:V- (cadr seg) p) tdir)) eps))
      (progn
        (setq lo (min (EL:Dot (EL:V- (car seg) p) tdir) (EL:Dot (EL:V- (cadr seg) p) tdir))
              hi (max (EL:Dot (EL:V- (car seg) p) tdir) (EL:Dot (EL:V- (cadr seg) p) tdir)))
        (if (> (- (min hi (- len eps)) (max lo eps)) eps)
          (setq blocked (cons (EL:Get 'id item) blocked)))))))
  (vl-sort (EL:Unique blocked) '<))
(defun EL:ValidateGapPair (a b snapshot cfg / p q tdir u v len ga gb ea eb c reason params blockers)
  (setq params (EL:Get 'params cfg) p (EL:Get 'point a) q (EL:Get 'point b)
        tdir (EL:Get 'direction a) u (EL:Get 'direction b))
  (cond ((or (EL:Get 'wire-attached a) (EL:Get 'wire-attached b)) (setq reason 'WIRE_ATTACHED_TO_EQUIPMENT))
        ((or (EL:Get 'occupied a) (EL:Get 'occupied b)) (setq reason 'ENDPOINT_OCCUPIED))
        ((equal (EL:Get 'wire a) (EL:Get 'wire b)) (setq reason 'SAME_ENTITY))
        ((not (and (equal (EL:Get 'geometry a) 'straight) (equal (EL:Get 'geometry b) 'straight)))
         (setq reason 'UNSUPPORTED_END_GEOMETRY))
        ((not (EL:LayerAllowed (EL:Get 'layer a) (EL:Get 'layer b) cfg)) (setq reason 'LAYER_REJECTED))
        ((> (abs (- (caddr p) (caddr q))) (EL:GapEpsilon)) (setq reason 'PLANE_REJECTED))
        (T
         (setq v (EL:V- q p) len (EL:Norm v) ga (EL:Dot v tdir) gb (EL:Dot (EL:V* -1.0 v) u)
               ea (abs (EL:Cross v tdir)) eb (abs (EL:Cross (EL:V* -1.0 v) u)) c (EL:Dot tdir (EL:V* -1.0 u)))
         (setq reason (cond ((<= len (EL:Get 'eps_touch params)) 'DIRECT_CONTACT)
            ((> len (EL:Get 'Dmax params)) 'OUT_OF_RANGE) ((or (<= ga 0.0) (<= gb 0.0)) 'BACKWARD)
            ((or (> ea (EL:GapEpsilon)) (> eb (EL:GapEpsilon))) 'LATERAL_REJECTED)
            ((or (> (EL:Norm (EL:V+ tdir u)) 1.0e-10)
                 (> (abs (caddr tdir)) 1.0e-10) (> (abs (caddr u)) 1.0e-10)) 'DIRECTION_REJECTED)
            ((setq blockers (EL:GapBlocked a b snapshot params)) 'BLOCKED_BY_DEVICE_OR_PATH)))))
  (list (cons 'target (EL:Get 'key b)) (cons 'accepted (not reason)) (cons 'reason reason)
        (cons 'distance len) (cons 'perp-a ea) (cons 'perp-b eb) (cons 'direction-dot c) (cons 'blockers blockers)))
(defun EL:CandidateLess (a b)
  (if (= (EL:Get 'distance a) (EL:Get 'distance b))
    (< (EL:Signature (EL:Get 'target a)) (EL:Signature (EL:Get 'target b)))
    (< (EL:Get 'distance a) (EL:Get 'distance b))))
(defun EL:FindGapCandidates (snapshot cfg / rows a b accepted rejected rec tree limit *EL:GapPathIndex* *EL:GapIndexReady*)
  ;; Complete forward corridor query; never stop at the first/nearest candidate.
  (setq tree (EL:SpatialTree (vl-remove-if-not 'EL:GapEligible (EL:Get 'ends snapshot)) 0)
        *EL:GapPathIndex* (EL:GapPathIndex snapshot) *EL:GapIndexReady* T
        limit (EL:Get 'Dmax (EL:Get 'params cfg)))
  (foreach a (EL:Get 'ends snapshot)
    (setq accepted nil rejected nil)
    (if (EL:GapEligible a)
      (foreach b (EL:SpatialRayQuery tree (EL:Get 'point a) (EL:Get 'direction a) limit)
        (if (not (equal (EL:Get 'key a) (EL:Get 'key b)))
          (progn
            (setq rec (EL:ValidateGapPair a b snapshot cfg))
            (if (EL:Get 'accepted rec) (setq accepted (cons rec accepted)) (setq rejected (cons rec rejected)))))))
    (setq rows (cons (list (cons 'key (EL:Get 'key a)) (cons 'candidates (vl-sort accepted 'EL:CandidateLess))
      (cons 'rejected (vl-sort rejected '(lambda (a b) (< (EL:Signature (EL:Get 'target a)) (EL:Signature (EL:Get 'target b))))))) rows)))
  (reverse rows))
(defun EL:By (key value records / result rec)
  (foreach rec records (if (equal (EL:Get key rec) value) (setq result rec))) result)
(princ)

;; Date: 2026-10-11. Absent DXF 60 and explicit zero both mean visible.
(defun EL:CanonicalVisibilityDXF (data)
  (vl-remove-if '(lambda (pair) (and (= (car pair) 60) (= (cdr pair) 0))) data))

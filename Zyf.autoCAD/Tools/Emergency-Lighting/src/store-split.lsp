;; Date: 2026-10-13. Immutable DWG chunks, one authoritative root switch.
(defun EL:SplitPairsWithout (keys data)
  (vl-remove-if '(lambda (pair) (member (car pair) keys)) data))
(defun EL:SplitEnvelope (kind value)
  (list '(schema-version . 1) '(drawing-uuid . "EL_SPLIT_CHUNK") '(diagrams)
    (cons 'chunk-kind kind) (cons 'chunk-value value)))
(defun EL:SplitAudit (key entry / native payload nativepayload)
  (EL:Require (and entry (equal (cdr (assoc 0 entry)) "XRECORD")
    (setq native (entget (cdr (assoc -1 entry))))
    (equal (cdr (assoc 0 native)) "XRECORD")) "拆分记录对象缺失，未继续读写。")
  ;; Date: 2026-10-13. Keep both complete native views, extract each only once.
  (setq payload (EL:StorePayload entry) nativepayload (EL:StorePayload native))
  (EL:StoreCheck payload nativepayload 'split-native)
  (list (cons 'key key) (cons 'entity (cdr (assoc -1 entry)))
    (cons 'payload payload)))
(defun EL:SplitChunkValid (context / entry native)
  (and (setq entry (dictsearch (namedobjdict) (EL:Get 'key context)))
    (equal (cdr (assoc -1 entry)) (EL:Get 'entity context))
    (equal (cdr (assoc 0 entry)) "XRECORD")
    (equal (EL:StorePayload entry) (EL:Get 'payload context))
    (setq native (entget (EL:Get 'entity context)))
    (equal (cdr (assoc 0 native)) "XRECORD")
    (equal (EL:StorePayload native) (EL:Get 'payload context))))
(defun EL:SplitVerifiedPayload (context kind / verified)
  ;; Date: 2026-10-13. Retain raw decode proof for one drawing, not source
  ;; freshness or a command context. Changed bytes must be decoded again.
  (setq verified (EL:Get (EL:Get 'key context) *EL:SplitVerifiedPayloads*))
  (and (equal *EL:SplitVerifiedOwner* (namedobjdict))
    (equal kind (EL:Get 'kind verified))
    (equal (EL:Get 'entity context) (EL:Get 'entity verified))
    (equal (EL:Get 'payload context) (EL:Get 'payload verified))))
(defun EL:SplitRememberVerified (context)
  (if (not (equal *EL:SplitVerifiedOwner* (namedobjdict)))
    (setq *EL:SplitVerifiedPayloads* nil *EL:SplitVerifiedOwner* (namedobjdict)))
  (setq *EL:SplitVerifiedPayloads* (EL:Put (EL:Get 'key context)
    (EL:SplitPairsWithout '(value) context) *EL:SplitVerifiedPayloads*)) nil)
(defun EL:SplitReadChunk (key kind / entry context cached envelope value)
  (setq entry (dictsearch (namedobjdict) key) context (EL:SplitAudit key entry)
    cached (EL:Get key *EL:SplitCache*))
  (if (and (equal *EL:SplitCacheOwner* (namedobjdict))
      (equal *EL:SplitCacheScope* *EL:StoreReadScope*)
      (equal (EL:Get 'entity context) (EL:Get 'entity cached))
      (equal (EL:Get 'payload context) (EL:Get 'payload cached))
      (equal kind (EL:Get 'kind cached)))
    (progn (setq value (EL:Get 'value cached)) (EL:PerfCount "split-decode-reuses" 1))
    (progn
      (setq envelope (EL:PerfCall "STORE_DECODE" 'EL:StoreDecode (list (EL:Get 'payload context))))
      (EL:Require (and (EL:StoreSchemaValid envelope)
        (equal (EL:Get 'drawing-uuid envelope) "EL_SPLIT_CHUNK")
        (equal kind (EL:Get 'chunk-kind envelope))) "拆分记录类型或版本不符，未继续。")
      (setq value (EL:Get 'chunk-value envelope))
      (EL:PerfCount "split-chunks-decoded" 1)))
  (EL:Require (EL:SplitChunkValid context) "拆分记录在解码期间变化，未使用。")
  (setq context (EL:Put 'kind kind (EL:Put 'value value context))
    *EL:SplitReadContexts* (EL:Put key context *EL:SplitReadContexts*)
    *EL:SplitCache* (EL:Put key context *EL:SplitCache*)
    *EL:SplitCacheOwner* (namedobjdict) *EL:SplitCacheScope* *EL:StoreReadScope*)
  (EL:SplitRememberVerified context) value)
(defun EL:SplitRoot (/ root)
  (if (dictsearch (namedobjdict) "EL_FIXED_SPLIT_V1")
    (progn
      (setq root (EL:SplitReadChunk "EL_FIXED_SPLIT_V1" 'root))
      (EL:Require (and (equal (EL:Get 'layout-version root) 1)
        (equal (type (EL:Get 'drawing-uuid root)) 'STR)
        (equal (type (EL:Get 'generation root)) 'INT)
        (listp (EL:Get 'items root))) "拆分根记录版本或字段无效，未继续。") root)))
(defun EL:SplitSummary (record / rows pair)
  (foreach pair record
    (if (member (car pair) '(diagram-id source-panel-handle panel-number engine status panel-output-handle power-only-target))
      (setq rows (cons pair rows))))
  (append (reverse rows) (list (cons 'history-circuit-count
    (length (cond ((EL:Get 'draft-circuits record)) (T (EL:ActualRows record))))))))
(defun EL:SplitRestoreRecord (item / detail pair key rows)
  (setq detail (EL:SplitReadChunk (EL:Get 'detail item) 'detail))
  (foreach key (EL:Get 'keys detail)
    (setq pair (assoc key (EL:Get 'small detail)))
    (if (not pair)
      (setq pair (cons key (EL:SplitReadChunk (EL:Get key (EL:Get 'blobs detail)) 'blob))))
    (setq rows (cons pair rows)))
  (setq rows (reverse rows))
  (EL:StoreCheck (EL:Get 'summary item) (EL:SplitSummary rows) 'split-index-record) rows)
(defun EL:SplitMaterialize (root / metadata rows key value)
  (setq metadata (EL:SplitReadChunk (EL:Get 'metadata root) 'metadata))
  (foreach value (EL:Get 'items root)
    (setq rows (cons (EL:SplitRestoreRecord value) rows)))
  (setq value nil)
  (foreach key (EL:Get 'keys root)
    (setq value (cons (if (equal key 'diagrams) (cons key (reverse rows))
      (assoc key metadata)) value)))
  (setq value (reverse value))
  (EL:Require (EL:StoreSchemaValid value) "拆分记录逻辑字段无效。")
  (EL:StoreCheck (EL:Get 'drawing-uuid root) (EL:Get 'drawing-uuid value) 'split-owner) value)
(defun EL:SplitRead (/ root *EL:SplitReadContexts*)
  (if (setq root (EL:SplitRoot)) (EL:SplitMaterialize root) (EL:StoreReadMonolithic)))
(defun EL:StoreIndex (/ root *EL:SplitReadContexts*)
  ;; A list read touches only the small root, no geometry/template chunks.
  (if (setq root (EL:SplitRoot))
    (list '(schema-version . 1) (cons 'drawing-uuid (EL:Get 'drawing-uuid root))
      (cons 'diagrams (mapcar '(lambda (item) (EL:Get 'summary item)) (EL:Get 'items root))))
    (EL:StoreReadMonolithic)))
(defun EL:StoreRecord (id / root item *EL:SplitReadContexts*)
  (if (setq root (EL:SplitRoot))
    (progn
      (setq item (vl-some '(lambda (row) (if (equal id (EL:Get 'diagram-id (EL:Get 'summary row))) row))
        (EL:Get 'items root)))
      (if item (EL:SplitRestoreRecord item)))
    (EL:By 'diagram-id id (EL:Get 'diagrams (EL:StoreReadMonolithic)))))
(defun EL:SplitViewP (store)
  (equal (EL:Get 'tag (EL:Get 'split-view store)) 'EL_INTERNAL_VIEW_V1))
(defun EL:SplitMetadata (store)
  (EL:SplitPairsWithout (if (EL:SplitViewP store) '(diagrams split-view) '(diagrams)) store))
(defun EL:SplitViewFromRoot (root result / metadata rows item summary selected selected-id lazy-ids value key)
  ;; Date: 2026-10-14. Hydrate only the selected history entry or the newest
  ;; entry for this box. Older outputs retain their exact immutable references.
  (setq metadata (EL:SplitReadChunk (EL:Get 'metadata root) 'metadata))
  (if (assoc 'split-view metadata) (EL:SplitMaterialize root) (progn
  (setq selected-id (EL:Get 'update-diagram-id result))
  (if (not selected-id)
    (foreach item (EL:Get 'items root)
      (setq summary (EL:Get 'summary item))
      (if (equal (EL:Get 'source-panel-handle summary) (EL:Get 'panel result))
        (setq selected-id (EL:Get 'diagram-id summary)))))
  (foreach item (EL:Get 'items root)
    (setq summary (EL:Get 'summary item)
      selected (and selected-id (equal (EL:Get 'diagram-id summary) selected-id)))
    (if (not selected) (setq lazy-ids (cons (EL:Get 'diagram-id summary) lazy-ids)))
    (setq rows (cons (if selected (EL:SplitRestoreRecord item)
      (EL:Put 'split-reference item summary)) rows)))
  (foreach key (EL:Get 'keys root)
    (setq value (cons (if (equal key 'diagrams) (cons key (reverse rows)) (assoc key metadata)) value)))
  (EL:Put 'split-view (list '(tag . EL_INTERNAL_VIEW_V1) (cons 'lazy-ids lazy-ids)
      (cons 'owner (namedobjdict)) (cons 'root root))
    (reverse value)))))
(defun EL:StoreForResult (result / root *EL:SplitReadContexts*)
  (if (setq root (EL:SplitRoot))
    (EL:PerfCall "STORE_CURRENT_BOX" 'EL:SplitViewFromRoot (list root result))
    (EL:StoreReadMonolithic)))
(defun EL:SplitAuditReachable (root / item detail key context cached)
  ;; Immutable references belonging to other boxes are retained byte-for-byte.
  ;; Audit both native routes without decoding their large geometry blobs.
  (foreach item (EL:Get 'items root)
    (setq detail (EL:SplitReadChunk (EL:Get 'detail item) 'detail))
    (foreach key (EL:Get 'blobs detail)
      (setq context (EL:SplitAudit (cdr key) (dictsearch (namedobjdict) (cdr key))))
      (if (not (EL:SplitVerifiedPayload context 'blob))
        (progn
          (EL:SplitReadChunk (cdr key) 'blob)
          (setq context (EL:Get (cdr key) *EL:SplitReadContexts*))))
      (setq context (EL:Put 'kind 'blob context))
      (setq cached (EL:Get (cdr key) *EL:SplitCache*))
      (if (and (equal *EL:SplitCacheOwner* (namedobjdict))
          (equal *EL:SplitCacheScope* *EL:StoreReadScope*)
          (equal (EL:Get 'entity context) (EL:Get 'entity cached))
          (equal (EL:Get 'payload context) (EL:Get 'payload cached)))
        (setq context cached))
      (setq *EL:SplitReadContexts* (EL:Put (cdr key) context *EL:SplitReadContexts*)))) T)
(defun EL:SplitCheckView (root store / item record reference metadata)
  (setq metadata (EL:SplitReadChunk (EL:Get 'metadata root) 'metadata))
  (EL:StoreCheck (EL:SplitMetadata store) metadata 'split-view-metadata)
  (EL:StoreCheck (length (EL:Get 'diagrams store)) (length (EL:Get 'items root)) 'split-view-count)
  (foreach record (EL:Get 'diagrams store)
    (setq item (vl-some '(lambda (row)
      (if (equal (EL:Get 'diagram-id (EL:Get 'summary row)) (EL:Get 'diagram-id record)) row)) (EL:Get 'items root))
      reference (if (member (EL:Get 'diagram-id record) (EL:Get 'lazy-ids (EL:Get 'split-view store)))
        (EL:Get 'split-reference record)))
    (EL:Require item "当前箱体视图与根索引不符。")
    (if reference
      (EL:StoreCheck record (EL:Put 'split-reference item (EL:Get 'summary item)) 'split-view-reference)
      (EL:StoreCheck record (EL:SplitRestoreRecord item) 'split-view-record))) T)
(defun EL:SplitNewChunk (key kind value / chunks decoded entity entry context)
  (setq chunks (EL:LogCall "STORE_SERIALIZE" (list (cons 'kind kind)) 'EL:StoreEncode
    (list (EL:SplitEnvelope kind value)))
    decoded (EL:LogCall "STORE_PARSE" nil 'EL:StoreDecode (list chunks)))
  (EL:StoreCheck (EL:SplitEnvelope kind value) decoded 'split-pre-write)
  (EL:Require (not (dictsearch (namedobjdict) key)) "拆分记录键已存在，未覆盖。")
  (setq entity (EL:StoreCreatePayload chunks 1))
  (EL:Require (and entity (dictadd (namedobjdict) key entity)) "拆分记录写入失败。")
  (setq entry (dictsearch (namedobjdict) key) context (EL:SplitAudit key entry))
  (EL:StoreCheck entity (EL:Get 'entity context) 'split-association)
  (EL:StoreCheck chunks (EL:Get 'payload context) 'split-readback)
  (setq context (EL:Put 'kind kind (EL:Put 'value value context))
    *EL:SplitReadContexts* (EL:Put key context *EL:SplitReadContexts*)
    *EL:SplitPool* (cons context *EL:SplitPool*)
    *EL:SplitCache* (EL:Put key context *EL:SplitCache*)
    *EL:SplitCacheOwner* (namedobjdict) *EL:SplitCacheScope* *EL:StoreReadScope*)
  ;; Pre-write decode and both complete native readbacks already passed.
  ;; The regular cache rechecks raw data before reusing this decoded value.
  (EL:SplitRememberVerified context)
  (EL:PerfCount "split-preverified-chunks" 1)
  (EL:PerfCount "split-chunks-written" 1) key)
(defun EL:SplitPut (kind value / found key)
  ;; Exact equality after native verification; no truncated signatures/hashes.
  (setq found (vl-some '(lambda (context)
    (if (and (assoc 'value context) (equal kind (EL:Get 'kind context))
      (equal value (EL:Get 'value context))) context)) *EL:SplitPool*))
  (if found (progn (EL:PerfCount "split-chunks-reused" 1) (EL:Get 'key found))
    (progn
      (setq key nil)
      (while (or (not key) (dictsearch (namedobjdict) key))
        (setq *EL:SplitSequence* (1+ *EL:SplitSequence*) key
          (strcat "EL_SPLIT_" (itoa *EL:SplitGeneration*) "_" (itoa *EL:SplitSequence*))))
      (EL:SplitNewChunk key kind value))))
(defun EL:SplitRecordParts (record / blobs pair detail)
  (foreach pair record
    (if (member (car pair) '(source-signature draft-source-signature template config))
      (setq blobs (cons (cons (car pair) (EL:SplitPut 'blob (cdr pair))) blobs))))
  (setq detail (list (cons 'keys (mapcar 'car record))
    (cons 'small (EL:SplitPairsWithout '(source-signature draft-source-signature template config) record))
    (cons 'blobs (reverse blobs))))
  (list (cons 'summary (EL:SplitSummary record)) (cons 'detail (EL:SplitPut 'detail detail))))
(defun EL:SplitBuild (store / items record reference)
  (foreach record (EL:Get 'diagrams store)
    (setq reference (if (and (EL:SplitViewP store)
      (member (EL:Get 'diagram-id record) (EL:Get 'lazy-ids (EL:Get 'split-view store))))
      (EL:Get 'split-reference record)))
    (if reference
      (progn
        (EL:Require (member reference (EL:Get 'items *EL:SplitViewRoot*)) "保存视图引用已变化。")
        (EL:StoreCheck record (EL:Put 'split-reference reference (EL:Get 'summary reference)) 'split-view-build)
        (setq items (cons reference items)) (EL:PerfCount "split-boxes-retained" 1))
      (setq items (cons (EL:SplitRecordParts record) items))))
  (list '(layout-version . 1) (cons 'drawing-uuid (EL:Get 'drawing-uuid store))
    (cons 'generation *EL:SplitGeneration*) (cons 'keys (mapcar 'car (if (EL:SplitViewP store) (EL:SplitPairsWithout '(split-view) store) store)))
    (cons 'metadata (EL:SplitPut 'metadata (EL:SplitMetadata store)))
    (cons 'items (reverse items))))
(defun EL:SplitBackup (entry / key old backup entity context suffix)
  (setq key "EL_FIXED_MONOLITH_BACKUP" old (EL:SplitAudit "EL_FIXED_V1" entry) suffix 0)
  (setq *EL:SplitReadContexts* (EL:Put "EL_FIXED_V1" old *EL:SplitReadContexts*))
  ;; A later explicit downgrade/remigration keeps every earlier raw backup.
  (while (and (setq backup (dictsearch (namedobjdict) key))
      (not (equal (EL:Get 'payload old) (EL:Get 'payload (EL:SplitAudit key backup)))))
    (setq suffix (1+ suffix) key (strcat "EL_FIXED_MONOLITH_BACKUP_" (itoa suffix))))
  (if (not backup)
    (progn
      (setq entity (EL:StoreCreatePayload (EL:Get 'payload old) 1))
      (EL:Require (and entity (dictadd (namedobjdict) key entity)) "旧保存记录原始备份失败。")
      (setq context (EL:SplitAudit key (dictsearch (namedobjdict) key)))
      (EL:StoreCheck entity (EL:Get 'entity context) 'split-backup-association)
      (EL:StoreCheck (EL:Get 'payload old) (EL:Get 'payload context) 'split-backup-raw))) T)
(defun EL:SplitContextValid (context)
  (and (equal (EL:Get 'owner context) (namedobjdict))
    (EL:Get 'verified-store context)
    (vl-every '(lambda (row) (EL:SplitChunkValid (cdr row))) (EL:Get 'split-contexts context))))
(defun EL:SplitWrite (store / root old entry staged chunks entity context value ids id record row baseline-contexts
    *EL:SplitReadContexts* *EL:SplitPool* *EL:SplitGeneration* *EL:SplitSequence* *EL:SplitViewRoot*)
  (EL:Require *EL:TransactionOpen* "拆分存储必须在完整事务中执行。")
  (EL:Require (EL:StoreSchemaValid store) "待保存记录字段无效，未写入。")
  (EL:CompactTemplates store)
  (EL:FreshBoundary)
  (setq *EL:SplitSequence* 0 *EL:StoreContextCandidate* nil *EL:StoreContextCommitted* nil)
  (foreach record (EL:Get 'diagrams store)
    (setq id (EL:Get 'diagram-id record))
    (EL:Require (and id (not (member id ids))) "保存记录身份缺失或重复，未写入。")
    (setq ids (cons id ids)))
  (setq root (EL:SplitRoot) *EL:SplitViewRoot* root
    *EL:SplitGeneration* (if root (1+ (EL:Get 'generation root)) 1))
  (if (EL:SplitViewP store)
    (EL:Require (and root (equal (EL:Get 'owner (EL:Get 'split-view store)) (namedobjdict))
      (equal root (EL:Get 'root (EL:Get 'split-view store)))) "保存列表已变化，请重新打开当前箱体。"))
  (if root (EL:StoreCheck (EL:Get 'drawing-uuid root) (EL:Get 'drawing-uuid store) 'split-drawing-owner))
  (if root
    (progn
      (if (EL:SplitViewP store)
        (progn (EL:SplitReadChunk (EL:Get 'metadata root) 'metadata) (EL:SplitAuditReachable root))
        (setq old (EL:SplitMaterialize root)))
      (foreach row *EL:SplitReadContexts* (setq *EL:SplitPool* (cons (cdr row) *EL:SplitPool*))))
    (if (setq entry (dictsearch (namedobjdict) "EL_FIXED_V1"))
      (progn
        (setq old (EL:StoreReadMonolithic))
        ;; Date: 2026-10-14. The exact raw backup keeps every old record.
        ;; Validate old template copies, then stage only the final store once.
        ;; Old/new native payloads are still checked before root publication.
        (EL:CompactTemplates old)
        (EL:LogCall "STORE_MIGRATE_BACKUP" nil 'EL:SplitBackup (list entry)))))
  (setq *EL:StoreReadCache* nil)
  (setq baseline-contexts *EL:SplitReadContexts*)
  (if old (EL:StoreCheck (EL:Get 'drawing-uuid old) (EL:Get 'drawing-uuid store) 'split-drawing-owner))
  (if (and root (equal old store))
    (progn (EL:PerfCount "split-noop-writes" 1) (setq value old))
    (progn
      (setq staged (EL:LogCall "STORE_STAGE_BUILD" nil 'EL:SplitBuild (list store)) *EL:SplitReadContexts* nil)
      (if (EL:SplitViewP store) (EL:SplitCheckView staged store)
        (EL:StoreCheck store (EL:SplitMaterialize staged) 'split-staged-logical))
      (if (and root (equal (EL:SplitPairsWithout '(generation) root)
          (EL:SplitPairsWithout '(generation) staged)))
        (progn (EL:PerfCount "split-noop-writes" 1)
          (setq *EL:SplitReadContexts* baseline-contexts value store))
        (progn
      (setq chunks (EL:StoreEncode (EL:SplitEnvelope 'root staged)))
      (EL:StoreCheck (EL:SplitEnvelope 'root staged) (EL:StoreDecode chunks) 'split-root-pre-write)
      (EL:Require (and (vl-every '(lambda (row) (EL:SplitChunkValid (cdr row))) baseline-contexts)
        (vl-every '(lambda (row) (EL:SplitChunkValid (cdr row))) *EL:SplitReadContexts*))
        "记录在准备期间变化，未发布拆分根。")
      ;; Root remains old until all reachable chunks have passed both native routes.
      (setq entry (dictsearch (namedobjdict) "EL_FIXED_SPLIT_V1") entity (cdr (assoc -1 entry)))
      (EL:PerfCount "master-write-attempts" 1)
      (EL:PerfCount "split-root-publications" 1)
      (if entity (EL:LogCall "STORE_REPLACE_PAYLOAD" nil 'EL:StoreReplacePayload (list entity chunks))
        (progn
          (setq entity (EL:StoreCreatePayload chunks 1))
          (EL:Require (and entity (dictadd (namedobjdict) "EL_FIXED_SPLIT_V1" entity)) "拆分根记录发布失败。")))
      (setq context (EL:SplitAudit "EL_FIXED_SPLIT_V1" (dictsearch (namedobjdict) "EL_FIXED_SPLIT_V1")))
      (EL:StoreCheck entity (EL:Get 'entity context) 'split-root-association)
      (EL:StoreCheck chunks (EL:Get 'payload context) 'split-root-readback)
      (setq *EL:SplitReadContexts* (EL:Put "EL_FIXED_SPLIT_V1" context *EL:SplitReadContexts*) value store)))))
  ;; Keep complete native post-commit checks for retained chunks as well.
  ;; The replaced root always uses its new audit, never its baseline payload.
  (if (EL:SplitViewP store)
    (foreach row baseline-contexts
      (if (and (not (equal (car row) "EL_FIXED_SPLIT_V1"))
          (not (assoc (car row) *EL:SplitReadContexts*)))
        (setq *EL:SplitReadContexts* (EL:Put (car row) (cdr row) *EL:SplitReadContexts*)))))
  (if *EL:StoreContextActive*
    (setq *EL:StoreContextCandidate* (list (cons 'owner (namedobjdict))
      (cons 'verified-store value) (cons 'split-contexts *EL:SplitReadContexts*))))
  (setq *EL:StoreWarmCache* nil)
  ;; Discard proofs for obsolete generations after each successful write.
  (setq *EL:SplitVerifiedPayloads* nil *EL:SplitVerifiedOwner* (namedobjdict))
  (foreach row *EL:SplitReadContexts*
    (if (EL:Get 'kind (cdr row)) (EL:SplitRememberVerified (cdr row))))
  (EL:FreshBoundary) T)
(defun EL:SplitDeactivate (/ entry entity)
  (EL:Require *EL:TransactionOpen* "旧格式转换必须在事务中执行。")
  (if (setq entry (dictsearch (namedobjdict) "EL_FIXED_SPLIT_V1"))
    (progn
      (setq entity (cdr (assoc -1 entry)))
      (EL:Require (dictremove (namedobjdict) "EL_FIXED_SPLIT_V1") "拆分根切换失败。")
      (entdel entity)
      (EL:Require (not (dictsearch (namedobjdict) "EL_FIXED_SPLIT_V1")) "拆分根仍生效，转换未完成。")))
  (setq *EL:SplitCache* nil) T)
(setq *EL:SplitStorageLoaded* T)
(princ)

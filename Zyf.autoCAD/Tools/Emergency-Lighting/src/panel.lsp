;; Date: 2026-10-16. Compact panel feedback; print overflow without splitting GB2312 pairs.
(defun EL:PanelText (key value / lines line units char cost index limit legacy step width)
  (setq width (if (member key '("dl_asset" "dl_status")) 34 44))
  (setq line "" units 0 index 1 limit (cond ((equal key "p_total") 4) ((equal key "dl_status") 3) (T 2)))
  (setq legacy (= (strlen "中") 2))
  (while (<= index (strlen value))
    (setq char (substr value index 1) cost (if (> (ascii char) 127) 2 1))
    (setq step (if (and legacy (= cost 2)) 2 1)
      char (substr value index step))
    (if (> (+ units cost) width)
      (setq lines (append lines (list line)) line "" units 0))
    (setq line (strcat line char) units (+ units cost) index (+ index step)))
  (setq lines (append lines (list line)) index 0)
  ;; Date: 2026-10-16. The footer is removed; keep details in the command line.
  (if (equal key "p_error")
    (if (/= value "") (princ (strcat "\n" value)))
    (progn
      (repeat limit
        (set_tile (if (= index 0) key (strcat key (itoa index))) (cond ((nth index lines)) (T "")))
        (setq index (1+ index)))
      (if (> (length lines) limit) (princ (strcat "\n" value))))))
;; Date: 2026-10-16. Action failures stay visible without a persistent footer.
(defun EL:PanelError (message)
  (EL:PanelText "p_error" message)
  (alert message))
(defun EL:ThumbRestore (/ item checked pending)
  (foreach item *EL:ThumbHidden*
    ;; Date: 2026-10-12. A rejected hide on a locked layer needs no write to restore.
    (if (not (equal (vl-catch-all-apply 'vla-get-Visible (list (car item))) (cadr item)))
      (progn
        (setq checked (vl-catch-all-apply 'vla-put-Visible (list (car item) (cadr item))))
        (if (or (vl-catch-all-error-p checked)
                (not (equal (vl-catch-all-apply 'vla-get-Visible (list (car item))) (cadr item))))
          (setq pending (cons item pending))))))
  (setq *EL:ThumbHidden* pending)
  (not pending))
(defun c:ELTHUMBRESET ()
  (princ (if (EL:ThumbRestore) "\n图例预览可见性已恢复。" "\n仍有对象未恢复，请检查锁层后重试。"))
  (vl-catch-all-apply 'vla-Regen (list (vla-get-ActiveDocument (vlax-get-acad-object)) 1)) (princ))
(defun EL:ThumbCleanup (/ path job)
  (EL:ThumbRestore)
  (foreach path *EL:ThumbSlides* (vl-catch-all-apply 'vl-file-delete (list path)))
  (foreach job *EL:ThumbJobs* (EL:DLCaptureCleanup job))
  (setq *EL:ThumbSlides* nil *EL:ThumbCache* nil *EL:ThumbSources* nil *EL:ThumbJobs* nil *EL:ThumbPending* nil))
(defun EL:ThumbDraw (key geometry / w h screen scale sw sh checked shown)
  (setq w (dimx_tile key) h (dimy_tile key))
  (start_image key) (fill_image 0 0 w h -15)
  (if (and geometry (findfile (car geometry)) (setq screen (cadr geometry))
      (numberp (car screen)) (> (car screen) 0) (numberp (cadr screen)) (> (cadr screen) 0))
    (progn
      (fill_image 0 0 w h -2)
      (setq scale (min (/ (float w) (car screen)) (/ (float h) (cadr screen)))
        sw (max 1 (fix (* scale (car screen)))) sh (max 1 (fix (* scale (cadr screen)))))
      (setq checked (vl-catch-all-apply 'slide_image
        (list (fix (/ (- w sw) 2)) (fix (/ (- h sh) 2)) sw sh (car geometry)))
        shown (and (not (vl-catch-all-error-p checked)) checked))
      (if (not shown) (progn (fill_image 0 0 w h -15)
        (EL:LogEvent "DEVICE_LEGEND_DRAW_FAILED" (list (cons 'tile key) (cons 'path (car geometry))
          (cons 'message (if (vl-catch-all-error-p checked) (vl-catch-all-error-message checked) "slide_image returned nil"))))))))
  (end_image) shown)
(defun EL:FixedSourceSignature (snapshot)
  (list 'EL_FIXED_SOURCE_V1 (EL:StableSnapshot snapshot)))
(defun EL:CircuitSnapshot (snapshot panel / blocks b)
  (foreach b (EL:Get 'blocks snapshot)
    (setq blocks (cons (EL:Put 'identity (EL:FixedBlockIdentity (EL:Get 'name b))
      (EL:Put 'role (EL:FixedBlockRole b panel nil) b)) blocks)))
  (EL:Put 'signature (EL:LogCall "SNAPSHOT_SIGNATURE" nil 'EL:FixedSourceSignature (list snapshot)) (EL:Put 'blocks (reverse blocks) snapshot)))
(defun EL:SplitNetwork (network cfg / snapshot panel edges seeds wire block i circuits result circuit
    *EL:DeviceContactCache* *EL:DeviceTemplateCache* *EL:DeviceTemplateEnabled*)
  ;; Date: 2026-10-15. Reuse definitions only for this call's identical
  ;; network, DWG owner and epoch. Keep original instance/pose creation order
  ;; and arithmetic; standalone splits still start with fresh caches.
  (if (and *EL:RecognitionPass* *EL:RecognitionContacts*
      (eq network (car *EL:RecognitionContacts*))
      (equal (namedobjdict) (cadr *EL:RecognitionContacts*))
      (equal *EL:FreshEpoch* (caddr *EL:RecognitionContacts*)))
    (setq *EL:DeviceTemplateCache* (nth 3 *EL:RecognitionContacts*)))
  (setq snapshot (EL:CircuitSnapshot (EL:Get 'snapshot network) (EL:Get 'panel network))
        panel (EL:Get 'panel network) block (EL:By 'id panel (EL:Get 'blocks snapshot)) i 0)
  (foreach wire (vl-sort (EL:Get 'wires snapshot) '(lambda (a b) (< (EL:Get 'id a) (EL:Get 'id b))))
    (if (cond ((EL:Get 'circuit-starts snapshot) (EL:By 'wire (EL:Get 'id wire) (EL:Get 'circuit-starts snapshot)))
        ((EL:Get 'trunk-segments snapshot) (member (EL:Get 'id wire) (EL:Get 'trunk-roots snapshot)))
        (T (EL:PathBlockHit wire block cfg)))
      (progn (setq i (1+ i))
        (setq seeds (cons (list (cons 'id (strcat "R" (itoa i))) (cons 'wire (EL:Get 'id wire))
          (cons 'key (list (EL:Get 'id wire) 'outlet))) seeds)))))
  (setq edges (vl-remove-if '(lambda (e) (member panel e)) (EL:Get 'edges network)))
  (setq *EL:DeviceTemplateEnabled* T)
  (foreach wire (reverse seeds)
    (setq circuit (EL:PerfCall "CIRCUIT_TRACE" 'EL:TraceCircuit
      (list wire snapshot edges (EL:Get 'gap-issues network))))
    (setq circuit (EL:Put 'number-scope (EL:PerfCall "CIRCUIT_NUMBER_SCOPE" 'EL:ExitNumberScope
      (list wire network cfg)) circuit) circuits (cons circuit circuits)))
  (foreach wire (reverse circuits)
    (EL:LogEvent "CIRCUIT_TRACE_RESULT" (list (cons 'id (EL:Get 'id wire))
      (cons 'wires (EL:Get 'wires wire)) (cons 'devices (EL:Get 'devices wire))
      (cons 'complete (EL:Get 'complete wire)) (cons 'issues (EL:Get 'issues wire)))))
  (list (cons 'panel panel) (cons 'drawing (EL:Get 'drawing snapshot)) (cons 'snapshot snapshot)
    (cons 'rules (EL:RecognitionRules cfg)) (cons 'circuits (reverse circuits))
    (cons 'complete (and circuits (not (EL:Get 'issues snapshot))
      (vl-every '(lambda (c) (EL:Get 'complete c)) circuits))) (cons 'engine 'fixed)))
(defun EL:NamePowerRecords (result powers / records b w entry)
  (foreach b (EL:Get 'blocks (EL:Get 'snapshot result))
    (setq w (EL:Get (strcase (EL:Get 'name b)) powers))
    (if (numberp w)
      (setq records (cons (list (cons 'identity (EL:Get 'identity b)) '(category . other)
        (cons 'display (if (and (assoc 'device-library result) (setq entry (EL:Get 'entry (EL:DLReference (EL:Get 'name b) result))))
          (EL:Get 'display entry) (EL:Get 'name b))) (cons 'watts w) '(zero-confirmed . T)) records)))) records)
;; Date: 2026-10-13. Ownership is checked before removing non-load objects.
(defun EL:FixedOwnership (circuits snapshot / out circuit other id block shared issues)
  (foreach circuit circuits
    (setq shared nil issues (vl-remove-if '(lambda (i) (equal (EL:Get 'code i) 'CIRCUIT_OWNERSHIP_CONFLICT)) (EL:Get 'issues circuit)))
    (foreach id (EL:Get 'objects circuit)
      (setq block (EL:By 'id id (EL:Get 'blocks snapshot)))
      (if (or (member id (EL:Get 'wires circuit)) (equal (EL:Get 'role block) 'junction))
        (foreach other circuits
          (if (and (not (equal (EL:Get 'id circuit) (EL:Get 'id other))) (member id (EL:Get 'objects other)))
            (setq shared (cons id shared))))))
    (if shared (setq issues (cons (EL:Issue 'CIRCUIT_OWNERSHIP_CONFLICT (EL:Get 'id circuit) (EL:Unique shared)) issues)))
    (setq out (cons (EL:Put 'complete (not issues) (EL:Put 'issues issues circuit)) out))) (reverse out))
(defun EL:SelectFixedExits (result excluded / circuits keys)
  (setq keys (mapcar '(lambda (c) (EL:Get 'key (EL:Get 'seed c))) (EL:Get 'circuits result))
    circuits (vl-remove-if '(lambda (c) (member (EL:Get 'key (EL:Get 'seed c)) excluded)) (EL:Get 'circuits result))
    circuits (EL:FixedOwnership circuits (EL:Get 'snapshot result)))
  (EL:Put 'candidate-keys keys (EL:Put 'excluded-seeds excluded (EL:Put 'circuits circuits
    (EL:Put 'complete (and circuits (not (EL:Get 'issues (EL:Get 'snapshot result)))
      (vl-every '(lambda (c) (EL:Get 'complete c)) circuits)) result)))))
;; Date: 2026-10-16. Keep red, green and magenta families out of circuit previews.
(defun EL:CircuitColor (index)
  (nth (fix (rem index 24)) '(4 2 5 30 190 140 40 180 150 160 31 41 51 131 141 151 161 171 181 191 32 42 52 132)))
;; Date: 2026-10-11. Resolve source ByLayer/true colors before choosing preview colors.
(defun EL:ACIColorRGB (index / hue sector fraction high low middle value)
  (cond ((<= index 9) (nth index '((255 255 255) (255 0 0) (255 255 0) (0 255 0)
      (0 255 255) (0 0 255) (255 0 255) (255 255 255) (128 128 128) (192 192 192))))
    ((>= index 250) (setq value (nth (- index 250) '(51 80 105 130 190 255))) (list value value value))
    (T
      (setq hue (fix (/ (- index 10) 10)) sector (fix (/ hue 4)) fraction (/ (rem hue 4) 4.0)
        high (nth (fix (/ (rem (- index 10) 10) 2)) '(255 204 153 127 76))
        low (if (= (rem index 2) 1) (fix (/ high 2.0)) 0)
        middle (fix (+ low (* (- high low) (if (= (rem sector 2) 0) fraction (- 1.0 fraction))))))
      (nth sector (list (list high middle low) (list middle high low) (list low high middle)
        (list low middle high) (list middle low high) (list high low middle))))))
(defun EL:PreviewEntityRGB (id / entity data color rgb)
  (if (and (setq entity (handent id)) (setq data (entget entity)))
    (progn
      (setq color (cond ((cdr (assoc 62 data))) (T 256)))
      (if (and (not (assoc 420 data)) (= color 256))
        (setq data (tblsearch "LAYER" (cdr (assoc 8 data)))))
      (if (setq rgb (cdr (assoc 420 data)))
        (list (logand 255 (fix (/ rgb 65536))) (logand 255 (fix (/ rgb 256))) (logand 255 rgb))
        (EL:ACIColorRGB (abs (cond ((cdr (assoc 62 data))) (T 7))))))))
(defun EL:PreviewPalette (result / ids wire circuit id colors rgb choices palette used candidate index)
  (foreach wire (EL:Get 'wires (EL:Get 'snapshot result))
    (setq ids (cons (cond ((EL:Get 'source-wire wire)) ((EL:Get 'id wire))) ids)))
  (if (not ids)
    (foreach circuit (EL:Get 'circuits result) (setq ids (append ids (EL:Get 'wires circuit)))))
  (foreach id (EL:Unique ids)
    (if (setq rgb (EL:PreviewEntityRGB id)) (setq colors (cons rgb colors))))
  (setq index 0)
  (repeat 24 (setq choices (append choices (list (EL:CircuitColor index))) index (1+ index)))
  ;; Only orange/yellow (30-59) and cyan/blue/violet (130-199), including shades.
  (setq candidate 30)
  (repeat 30 (setq choices (append choices (list candidate)) candidate (1+ candidate)))
  (setq candidate 130)
  (repeat 70 (setq choices (append choices (list candidate)) candidate (1+ candidate)))
  (foreach candidate choices
    (setq rgb (EL:ACIColorRGB candidate))
    (if (and (not (member rgb used))
        (not (vl-some '(lambda (source) (< (EL:Dot (EL:V- rgb source) (EL:V- rgb source)) 10000.0)) colors)))
      (setq palette (append palette (list candidate)) used (cons rgb used))))
  palette)
;; Date: 2026-10-16. The panel and drawing preview consume the same ordered palette.
(defun EL:PanelCircuitColorsDraw (palette / index key color width height)
  (setq index 0)
  (repeat 8
    (setq key (strcat "p_color" (itoa index)) color (nth index palette)
      width (dimx_tile key) height (dimy_tile key))
    (start_image key)
    (fill_image 0 0 width height 8)
    (fill_image 1 1 (max 1 (- width 2)) (max 1 (- height 2)) (if color color -15))
    (end_image)
    (setq index (1+ index))))
(defun EL:ColorPreviewCleanup (/ item checked pending)
  (foreach item *EL:ColorPreviewCopies*
    (setq checked (vl-catch-all-apply 'vla-Delete (list item)))
    (if (vl-catch-all-error-p checked) (setq pending (cons item pending))))
  (setq *EL:ColorPreviewCopies* pending pending nil)
  (foreach item *EL:ColorPreviewSources*
    (setq checked (vl-catch-all-apply 'vla-put-Visible (list (car item) (cadr item))))
    (if (vl-catch-all-error-p checked) (setq pending (cons item pending))))
  (setq *EL:ColorPreviewSources* pending)
  (redraw)
  (not (or *EL:ColorPreviewCopies* *EL:ColorPreviewSources*)))
(defun EL:ColorPreviewShape (object color depth / children child)
  (EL:Require (< depth 32) "设备嵌套过深，已停止着色预览。")
  (vla-put-Layer object "0")
  (vla-put-Visible object :vlax-true)
  (if (equal (vla-get-ObjectName object) "AcDbBlockReference")
    (progn
      (setq children (vlax-safearray->list (vlax-variant-value (vla-Explode object))))
      ;; Register every child before touching any of them, including on failure.
      (setq *EL:ColorPreviewCopies* (append children *EL:ColorPreviewCopies*))
      (EL:Require children "设备图块无法展开显示，已停止着色预览。")
      (foreach child children (EL:ColorPreviewShape child color (1+ depth)))
      (vla-Delete object)
      (setq *EL:ColorPreviewCopies* (vl-remove object *EL:ColorPreviewCopies*)))
    (vla-put-Color object color)))
(defun EL:ColorPreviewEntity (id color / entity object copy)
  (EL:Require (setq entity (handent id)) "回路对象已删除，请重新统计。")
  (setq object (vlax-ename->vla-object entity) copy (vla-Copy object))
  (setq *EL:ColorPreviewCopies* (cons copy *EL:ColorPreviewCopies*))
  (EL:ColorPreviewShape copy color 0)
  (setq *EL:ColorPreviewSources* (cons (list object (vla-get-Visible object)) *EL:ColorPreviewSources*))
  (vla-put-Visible object :vlax-false))
;; Date: 2026-10-10. Preview only the logical piece of a crossing source wire.
(defun EL:ColorPreviewWire (wire color / object space segment copy)
  (EL:Require (handent (EL:Get 'source-wire wire)) "集中出线源导线已删除，请重新统计。")
  (setq object (vlax-ename->vla-object (handent (EL:Get 'source-wire wire)))
    space (vla-get-ModelSpace (vla-get-ActiveDocument (vlax-get-acad-object))))
  (if (not (assoc object *EL:ColorPreviewSources*))
    (progn
      (setq *EL:ColorPreviewSources* (cons (list object (vla-get-Visible object)) *EL:ColorPreviewSources*))
      (vla-put-Visible object :vlax-false)))
  (foreach segment (EL:Get 'segments wire)
    (setq copy (vla-AddLine space (vlax-3d-point (car segment)) (vlax-3d-point (cadr segment)))
      *EL:ColorPreviewCopies* (cons copy *EL:ColorPreviewCopies*))
    (EL:ColorPreviewShape copy color 0)))
(defun EL:AllCircuitColorWait (result / circuit index ids id seen snapshot wire block bounds lo hi palette color)
  (EL:Require (EL:ColorPreviewCleanup) "上次预览尚未清理完成，请运行 ELCOLORRESET。")
  (EL:ClearGapPreview) (EL:ClearPickHighlights)
  ;; Shared objects have no unambiguous circuit color: reject before any writes.
  (EL:Require (<= (length (EL:Get 'circuits result)) 24) "当前分色支持最多 24 条回路。")
  (setq palette (cond (*EL:PanelPreviewPalette*) (T (EL:PreviewPalette result))))
  (EL:Require (>= (length palette) (length (EL:Get 'circuits result)))
    "原导线颜色过多，无法分配清晰的回路预览颜色。")
  (foreach circuit (EL:Get 'circuits result)
    (setq ids (EL:Unique (append (EL:Get 'wires circuit) (EL:Get 'devices circuit))))
    (foreach id ids
      (EL:Require (not (member id seen)) "发现多回路共用对象，请先核对连接。")
      (setq seen (cons id seen))))
  (setq snapshot (EL:Get 'snapshot result))
  (foreach id seen
    (setq wire (EL:By 'id id (EL:Get 'wires snapshot)) block (EL:By 'id id (EL:Get 'blocks snapshot))
      bounds (if wire (EL:SegmentBounds (EL:Get 'segments wire)) (EL:Get 'bounds block)))
    (if bounds (setq lo (if lo (mapcar 'min lo (car bounds)) (car bounds))
      hi (if hi (mapcar 'max hi (cadr bounds)) (cadr bounds)))))
  (if lo (EL:SimpleZoom lo hi))
  (setq index 0)
  (foreach circuit (EL:Get 'circuits result)
    (setq color (nth index palette))
    (foreach id (EL:Unique (append (EL:Get 'wires circuit) (EL:Get 'devices circuit)))
      (setq wire (EL:By 'id id (EL:Get 'wires snapshot)))
      (if (EL:Get 'source-wire wire) (EL:ColorPreviewWire wire color)
        (EL:ColorPreviewEntity id color)))
    (princ (strcat "\nZE" (itoa (1+ index)) "：预览颜色 " (itoa color)))
    (setq index (1+ index)))
  (redraw)
  (EL:PerfInput 'getstring (list "\n已识别路径已改为区别于原导线的颜色；保留原色的部分未纳入回路。按 Enter 或 Esc 返回：")))
(defun EL:AllCircuitColorPreview (result / checked document clean ended checkpoint)
  ;; One undo group prevents stepping through a half-restored preview.
  (setq document (vla-get-ActiveDocument (vlax-get-acad-object)))
  (vla-StartUndoMark document)
  (setq checkpoint *EL:PerfPending* checked (vl-catch-all-apply 'EL:AllCircuitColorWait (list result)))
  (EL:PerfUnwind checkpoint)
  (setq clean (EL:ColorPreviewCleanup)
    ended (vl-catch-all-apply 'vla-EndUndoMark (list document)))
  (if (not clean)
    (EL:Require nil "预览清理未完成，请运行 ELCOLORRESET 重试，清理前不要保存图纸。"))
  (if (vl-catch-all-error-p ended) (EL:Require nil "预览撤销组未能结束，请检查 CAD 命令状态。"))
  (if (vl-catch-all-error-p checked)
    (princ (strcat "\n已结束回路分色预览：" (vl-catch-all-error-message checked)))))
(defun c:ELCOLORRESET ()
  (princ (if (EL:ColorPreviewCleanup) "\n回路分色预览已清理。" "\n仍有对象未能恢复，请检查图层锁定状态后重试。")) (princ))
(defun EL:PanelCompute (result powers cfg / prepared *EL:StatisticsScopeEnabled*)
  (setq *EL:StatisticsScopeEnabled* T)
  (if (assoc 'device-library result)
    (progn
      (if (not (EL:DLRefsCover result))
        (progn (if (not *EL:DLSessionSnapshot*) (setq *EL:DLSessionSnapshot* (EL:DLSnapshot)))
          (setq prepared (EL:DLPrepare result powers *EL:DLSessionSnapshot* nil) result (EL:Get 'result prepared) powers (EL:Get 'powers prepared))))
      (setq powers (EL:DLEffectivePowers result powers) result (EL:Put 'effective-powers powers result))))
  (setq result (EL:BoxStatistics result (EL:Put 'powers (EL:NamePowerRecords result powers) cfg) nil nil))
  (if (assoc 'device-library result) (setq result (EL:DLEvaluate result powers)))
  (EL:Put 'can-generate (and (EL:Get 'can-generate result) (EL:CircuitNumbersReady result)) result))
(defun EL:MatchCircuits (circuits saved prefix / out old c key seen next removed added)
  (setq next 1)
  (foreach old saved (if (numberp (EL:Get 'output-order old)) (setq next (max next (1+ (EL:Get 'output-order old))))))
  (foreach c circuits
    (setq key (EL:Get 'key (EL:Get 'seed c)) old (EL:By 'seed-key key saved))
    (if (or (not key) (member key seen)) (setq key nil))
    (if key
      (progn
        (setq seen (cons key seen))
        (if (not old)
          (progn
            (while (EL:By 'circuit-uid (strcat prefix "/" (EL:Signature key) "/" (itoa next)) saved) (setq next (1+ next)))
            (setq old (list (cons 'circuit-uid (strcat prefix "/" (EL:Signature key) "/" (itoa next)))
              (cons 'output-order next) '(is-ground) '(ground-source . default))
              next (1+ next) added T)))
        (foreach key '(circuit-uid output-order is-ground ground-source ground-rule ground-evidence)
          (setq c (EL:Put key (EL:Get key old) c)))
        (setq c (EL:Put 'seed-key (EL:Get 'key (EL:Get 'seed c)) c) out (cons c out)))
      (setq out (cons (EL:Put 'identity-error T c) out))))
  (setq removed (vl-remove-if '(lambda (r) (member (EL:Get 'seed-key r) seen)) saved))
  (list (cons 'circuits (vl-sort out '(lambda (a b) (< (cond ((EL:Get 'output-order a)) (T 0))
    (cond ((EL:Get 'output-order b)) (T 0)))))) (cons 'removed removed) (cons 'added added)
    (cons 'ambiguous (or removed (vl-some '(lambda (c) (EL:Get 'identity-error c)) out)))))
(defun EL:GroundSuggestion (circuit names version blocks / hits id b)
  ;; No configured names => no inference. Explicit manual yes AND no win.
  (if (equal (EL:Get 'ground-source circuit) 'manual) circuit
    (progn
      (if (and names (EL:Get 'complete circuit))
        (foreach id (EL:Get 'devices circuit)
          (setq b (EL:By 'id id blocks))
          (if (member (EL:Get 'name b) names) (setq hits (cons id hits)))))
      (EL:Put 'is-ground (if hits T nil) (EL:Put 'ground-source (if names 'auto-rule 'default)
        (EL:Put 'ground-rule version (EL:Put 'ground-evidence hits circuit)))))))
;; Date: 2026-10-14. Restore old per-block ground choices without rescanning.
(defun EL:PanelBlockGroundApply (/ cs c id block hits settings)
  (if (not (assoc 'device-library *EL:PanelDraft*))
    (progn
      (setq settings (EL:Get 'block-ground *EL:PanelDraft*))
      (foreach c (EL:Get 'circuits *EL:PanelDraft*)
        (setq hits nil)
        (foreach id (EL:Get 'devices c)
          (setq block (EL:By 'id id (EL:Get 'blocks (EL:Get 'snapshot *EL:PanelDraft*))))
          (if (EL:Get (strcase (EL:Get 'name block)) settings) (setq hits (cons id hits))))
        (setq cs (cons (EL:Put 'ground-evidence hits (EL:Put 'ground-rule 'block-table
          (EL:Put 'ground-source 'manual (EL:Put 'is-ground (if hits T nil) c)))) cs)))
      (setq *EL:PanelDraft* (EL:Put 'circuits (reverse cs) *EL:PanelDraft*)))))
(defun EL:CapacityDefault (capacity)
  ;; Date: 2026-10-09. Use 0.3kW immediately; retain a valid saved choice.
  (if (member capacity '(cap300 cap600 cap1000)) capacity 'cap300))
(defun EL:SelectionsReady (result capacity)
  ;; Date: 2026-10-11. Ground values need no separate confirmation state.
  (if (member capacity '(cap300 cap600 cap1000)) T nil))
;; Date: 2026-10-16. Reopen two shared layouts without reading hidden editor tiles.
(defun EL:PanelClose (status)
  (setq *EL:PanelDialogPosition* (done_dialog status)))
(defun EL:PanelLibraryFlush ()
  (or (not *EL:PanelLibraryExpanded*) (not *EL:PanelLibrarySnapshot*) (EL:DLUIFlush)))
(defun EL:PanelLeave (status)
  (if (EL:PanelLibraryFlush) (EL:PanelClose status)))
;; Date: 2026-10-16. Always close on Esc/X; keep even invalid editor input in session drafts.
(defun EL:PanelExit ()
  (if (and *EL:PanelLibraryExpanded* *EL:PanelLibrarySnapshot*)
    (progn
      (setq *EL:DLUIState* (EL:Put 'query (get_tile "dl_query")
        (EL:Put 'deleted (equal (get_tile "dl_deleted") "1") *EL:DLUIState*)))
      (EL:DLUISafe 'EL:DLUIStore)
      ;; Keep the saved snapshot current without recomputing a panel that is closing.
      (setq *EL:DLSessionSnapshot* (EL:Get 'snapshot *EL:DLUIState*))))
  (EL:PanelClose 0))
(defun EL:PanelLibraryToggle ()
  (if (EL:PanelLibraryFlush)
    (progn
      (if (and *EL:PanelLibraryExpanded* *EL:PanelLibrarySnapshot*)
        (progn
          (setq *EL:DLUIState* (EL:Put 'query (get_tile "dl_query")
            (EL:Put 'deleted (equal (get_tile "dl_deleted") "1") *EL:DLUIState*)))
          (EL:PanelLibraryReconcile)))
      (setq *EL:PanelLibraryExpanded* (not *EL:PanelLibraryExpanded*))
      (EL:PanelClose 21))))
(defun EL:PanelNewDialog (dialog / name)
  (setq name (if *EL:PanelLibraryExpanded* "el_panel" "el_panel_compact"))
  (if *EL:PanelDialogPosition*
    (new_dialog name dialog "" *EL:PanelDialogPosition*)
    (new_dialog name dialog)))
;; Date: 2026-10-16. Keep all recognized circuits and explain the fixed eight-row limit.
(defun EL:PanelCircuitLimitText (result / count)
  (setq count (length (EL:Get 'circuits result)))
  (if (> count 8)
    (strcat "已识别 " (itoa count) " 条实际回路；当前系统图最多容纳 8 条。"
      "\n面板仅显示前 8 条，全部回路数据已保留，不会截断。"
      "\n请拆分配电箱或重新选择回路后再生成。")))
(defun EL:PanelGenerateBody (/ limit)
  (EL:LogEvent "PANEL_ACTION" 'generate)
  (if (setq limit (EL:PanelCircuitLimitText *EL:PanelDraft*))
    (EL:PanelError limit)
    (if (EL:DLPanelSubmissionReady)
      (cond
        ((not (EL:Get 'circuits *EL:PanelDraft*)) (EL:PanelError "请至少保留一条实际出线。"))
        ((not (EL:CircuitNumbersReady *EL:PanelDraft*))
          (EL:PanelError (EL:NumberProblemText *EL:PanelDraft*)))
        ((not (EL:Get 'can-generate *EL:PanelDraft*)) (EL:PanelGenerationBlocked *EL:PanelDraft*))
        ((not (EL:SelectionsReady *EL:PanelDraft* *EL:PanelCapacity*))
          (EL:PanelError "请先选择箱体容量。"))
        (*EL:PanelTemplateReady* (setq *EL:PanelAction* 'generate) (EL:PanelClose 2))
        (T (setq *EL:PanelAction* 'generate) (EL:PanelClose 4)))
      (alert (if *EL:DLError*
        (strcat *EL:DLError* "\n请在设备库中检查并恢复；当前面板输入保留，恢复后可再次生成。")
        "设备库默认值已刷新，请核对当前功率和地面属性后再次生成。")))))
(defun EL:PanelGenerate (/ outcome)
  ;; Date: 2026-10-10. Keep callback failures visible while preserving the draft.
  ;; Date: 2026-10-16. Report excess circuits before editor validation can hide the limit.
  (if (or (EL:PanelCircuitLimitText *EL:PanelDraft*) (EL:PanelLibraryFlush))
    (setq outcome (vl-catch-all-apply 'EL:PanelGenerateBody nil)))
  (if (vl-catch-all-error-p outcome)
    (progn
      (setq *EL:PanelAction* nil)
      (EL:LogEvent "PANEL_GENERATE_ERROR" (vl-catch-all-error-message outcome))
      (EL:PanelText "p_error" (strcat "生成未开始：" (vl-catch-all-error-message outcome)))
      (alert (strcat "生成未开始：" (vl-catch-all-error-message outcome) "\n当前设置已保留，请查看诊断日志。")))))
(defun EL:PanelFill (/ cs i c key ids circuit total)
  (setq cs (EL:Get 'circuits *EL:PanelDraft*) i 0)
  (repeat 8
    (setq c (nth i cs) key (itoa i))
    (set_tile (strcat "p_row" key)
      ;; Date: 2026-10-10. Display output numbering and watts only.
      (if c (strcat (EL:CircuitNumberText c (1+ i))
        (if (and (assoc 'number-status c) (not (equal (EL:Get 'number-status c) 'ready))) " [待核对]" "")
        " | " (itoa (EL:Get 'watts c)) "W")
        (if (< i (EL:FixedOutputCount (length cs)))
          (strcat "预留" (itoa (1+ (- i (length cs))))) "")))
    (setq i (1+ i)))
  (foreach circuit cs (setq ids (append ids (EL:Get 'devices circuit))))
  ;; Date: 2026-10-16. Show deduplicated power below the rows; keep counts in the command line.
  (setq total (EL:PanelKnownTotal))
  (set_tile "p_power_total" total)
  (princ (strcat "\n已识别设备 " (itoa (length (EL:Unique ids)))
    " 个；待核对设备 " (itoa (length (EL:Get 'library-pending *EL:PanelDraft*))) " 种。"))
  (EL:PanelText "p_error" (cond
    ((not (EL:CircuitNumbersReady *EL:PanelDraft*)) (EL:NumberProblemText *EL:PanelDraft*))
    ((EL:Get 'load-error (EL:Get 'device-library *EL:PanelDraft*)) "设备库无法读取，请修复库文件后重新统计；本图和库原文件保留。")
    ((EL:Get 'library-pending *EL:PanelDraft*) (strcat "尚有 " (itoa (length (EL:Get 'library-pending *EL:PanelDraft*)))
      (if *EL:PanelLibraryExpanded* " 种设备待核对；请在右侧设备库补齐资料。"
        " 种设备待核对；请展开设备库补齐资料。")))
    ((not ids) "未识别到连接设备，请检查导线连接或设备图块。")
    ((and (not (assoc 'block-ground *EL:PanelDraft*)) (vl-some '(lambda (c) (EL:Get 'is-ground c)) cs))
      "沿用旧回路地面设置；修改图块地面勾选后按图块统一重算。")
    (T "")))
  (princ (strcat "\n" total "；实际回路 " (itoa (length cs)) "；输出 " (itoa (EL:FixedOutputCount (length cs)))
    "；已完整核对回路 " (itoa (EL:Get 'box-watts *EL:PanelDraft*)) " W"))
  (set_tile "p_capacity" (cond ((equal *EL:PanelCapacity* 'cap600) "p_600")
    ((equal *EL:PanelCapacity* 'cap1000) "p_1000") (T "p_300")))
  (princ (strcat "\n" (if *EL:PanelTemplateReady* "模板已验证，生成时自动切换状态。"
    "模板未设置或已变化：点击生成时设置；不影响当前统计。")))
  (setq i 0)
  (foreach c cs
    (if (> (strlen (EL:CircuitNumberText c (1+ i))) 24)
      (princ (strcat "\n回路完整编号：" (EL:CircuitNumberText c (1+ i)))))
    (setq i (1+ i))))
(defun EL:PanelKnownTotal (/ ids circuit rows row total missing kinds overflow watts)
  (foreach circuit (EL:Get 'circuits *EL:PanelDraft*)
    (setq ids (append ids (EL:Get 'devices circuit))))
  (setq ids (EL:Unique ids) total 0 missing 0 kinds 0)
  (setq rows (EL:SimpleRows (vl-remove-if-not '(lambda (b) (member (EL:Get 'id b) ids))
    (EL:Get 'blocks (EL:Get 'snapshot *EL:PanelDraft*))) *EL:PanelPowers*))
  (foreach row rows
    (setq watts (EL:Get 'watts row))
    (if (numberp watts)
      (if (> watts (/ (- 2147483647 total) (EL:Get 'count row))) (setq overflow T)
        (setq total (+ total (* watts (EL:Get 'count row)))))
      (setq missing (+ missing (EL:Get 'count row)) kinds (1+ kinds))))
  (strcat (if (and (= missing 0) (EL:Get 'complete *EL:PanelDraft*)) "总功率：" "已知总功率：")
    (if overflow "超出整数范围" (strcat (itoa total) " W"))
    (if (> missing 0) (strcat "；尚有 " (itoa kinds) " 种 / " (itoa missing) " 个设备未填功率") "")
    (if (EL:Get 'complete *EL:PanelDraft*) "" "；连接仍待核对")))
(defun EL:PanelCapacity (value)
  (setq *EL:PanelCapacity* (cond ((equal value "p_600") 'cap600) ((equal value "p_1000") 'cap1000) (T 'cap300))
    *EL:PanelDraft* (EL:Put 'capacity-source 'manual *EL:PanelDraft*))
  (EL:PanelFill))
(defun EL:PanelAccept ()
  (EL:LogEvent "PANEL_ACTION" 'save)
  (if (and (EL:PanelLibraryFlush) (EL:DLPanelSaveReady))
    (if (EL:Get 'circuits *EL:PanelDraft*) (progn (setq *EL:PanelAction* 'save) (EL:PanelClose 1))
      (EL:PanelError "请至少保留一条实际出线。"))))
;; Date: 2026-10-16. Leave power uncounted until picking, without capacity helper rows.
(defun EL:PanelHomeFill (/ i key)
  (set_tile "p_number" "配电箱编号：请先拾取配电箱")
  (setq i 0)
  (repeat 8 (set_tile (strcat "p_row" (itoa i)) "") (setq i (1+ i)))
  (set_tile "p_power_total" "总功率：未统计")
  (EL:PanelText "p_error" "")
  (set_tile "p_capacity" "p_300")
  (foreach key '("p_trunk" "p_capacity" "f_preview" "p_generate") (mode_tile key 1)))
(defun EL:PanelLibraryReconcile (/ snapshot resolved)
  (setq snapshot (EL:Get 'snapshot *EL:DLUIState*))
  (if snapshot
    (progn
      (if (and *EL:DLSessionSnapshot*
          (equal (EL:Get 'root *EL:DLSessionSnapshot*) (EL:Get 'root snapshot))
          (equal (EL:Get 'raw *EL:DLSessionSnapshot*) (EL:Get 'raw snapshot))
          (equal (EL:Get 'catalog *EL:DLSessionSnapshot*) (EL:Get 'catalog snapshot)))
        (setq resolved nil)
        (setq resolved T))
      (setq *EL:PanelLibrarySnapshot* snapshot *EL:DLSessionSnapshot* snapshot)
      (if (and resolved *EL:PanelDraft*)
        (progn
          (setq resolved (EL:DLPrepare *EL:PanelDraft* *EL:PanelPowers* snapshot nil)
            *EL:PanelDraft* (EL:Get 'result resolved) *EL:PanelPowers* (EL:Get 'powers resolved)
            *EL:PanelDraft* (EL:PanelCompute *EL:PanelDraft* *EL:PanelPowers* *EL:PanelConfig*))
          T)))))
(defun EL:PanelLibraryStatus (deleted)
  (EL:DLUISafe (if deleted 'EL:DLUIPanelDelete 'EL:DLUIPanelRestore))
  (if (EL:PanelLibraryReconcile) (EL:PanelFill)))
(defun EL:DLUIPanelDelete () (EL:DLUIChangeStatus T))
(defun EL:DLUIPanelRestore () (EL:DLUIChangeStatus nil))
(defun EL:PanelLibraryExternal (status / entry result checkpoint path)
  (cond
    ((= status 15) (EL:DLLibraryTransferUI nil))
    ((= status 14)
      (setq *EL:DLUIDirectories* (EL:Put (EL:Get 'root (EL:Get 'snapshot *EL:DLUIState*))
        *EL:DLUIState* *EL:DLUIDirectories*))
      (setq path (getfiled "选择设备库的 catalog.eld" (strcat (EL:DLRoot) "catalog.eld") "eld" 0))
      (if path (EL:DLUISwitchRoot path)))
    ((= status 16) (EL:DLLibraryTransferUI T))
    ((= status 13)
      (setq checkpoint *EL:PerfPending* result (vl-catch-all-apply 'EL:DLPickDevices nil))
      (if (vl-catch-all-error-p result) (EL:PerfUnwind checkpoint))
      (if (and (not (vl-catch-all-error-p result)) result)
        (progn
          (setq *EL:DLUIPickQueue* result *EL:DLUIPickSaved* 0
            *EL:DLUIPickReused* 0 *EL:DLUIPickFailed* 0)
          (if (equal (EL:DLUIPickNext) 'suspended) (setq status 12)))
        (setq *EL:DLUINotice* "本次未拾取设备；现有资料和输入保留。"))))
  (if (= status 12) 12 (progn (EL:PanelLibraryReconcile) 3)))
;; Date: 2026-10-15. Open the bundled drawing without changing the current DWG.
(defun EL:PanelOpenBlockLibrary (/ path folder present outcome)
  (setq path (EL:SystemBlockLibraryPath))
  (if (and path (setq folder (vl-filename-directory path)) (vl-file-directory-p folder))
    (progn
      (setq present (findfile path)
        outcome (vl-catch-all-apply 'startapp
          (list "explorer.exe" (strcat (if present "/select,\"" "\"")
            (vl-string-translate "/" "\\" (if present path folder)) "\""))))
      (cond
        ((or (not outcome) (vl-catch-all-error-p outcome))
          "无法打开图块文件夹，请手动查看 templates/系统图块库.dwg。")
        (present "已打开系统图块库所在文件夹。")
        (T "已打开图块文件夹；尚缺系统图块库.dwg。")))
    "图块文件夹不存在，请重新解压完整交付包。"))
;; Date: 2026-10-16. Open only this export's successful result, keeping failure details intact.
(defun EL:PanelDiagnosticExportOpen (/ notice path opened)
  (setq *EL:DiagnosticExportPath* nil *EL:DiagnosticExportMessage* nil
    *EL:DiagnosticError* nil *EL:DiagnosticExportSucceeded* nil)
  (setq notice (EL:PanelDiagnosticExport) path *EL:DiagnosticExportPath*)
  (princ (strcat "\n" notice))
  (if path (princ (strcat "\n诊断资料路径：" path)))
  (if (and path *EL:DiagnosticExportSucceeded*)
    (progn
      (setq opened (EL:DiagnosticOpenFolder path))
      (princ (strcat "\n" opened))
      (if (not (equal opened "已打开诊断文件所在位置。"))
        (alert (strcat notice "\n" opened "\n诊断资料路径：" path))))
    (alert notice)))
(defun EL:PanelDialog (result cfg powers capacity / dialog status captured limit-notice limit-shown
    *EL:PanelAction* *EL:PanelDraft* *EL:PanelPowers* *EL:PanelCapacity* *EL:PanelConfig*
    *EL:PanelTemplateReady* *EL:PanelLibrarySnapshot* *EL:PanelDialogPosition* *EL:PanelPreviewPalette*
    home)
  (setq home (not result)
    *EL:PanelDraft* (if result (EL:PanelCompute (EL:SelectFixedExits result nil) powers cfg))
    *EL:PanelPowers* powers *EL:PanelCapacity* (EL:CapacityDefault capacity)
    *EL:PanelPreviewPalette* (EL:PreviewPalette *EL:PanelDraft*)
    *EL:PanelConfig* cfg
    *EL:PanelTemplateReady* (if result (EL:TemplateReady (EL:Get 'template cfg) cfg))
    *EL:PanelLibrarySnapshot* (cond (home (EL:DLSnapshot))
      (*EL:DLSessionSnapshot*) (T (EL:DLSnapshot)))
    dialog (load_dialog (strcat *EL:Root* "ui/power.dcl")) *EL:DialogID* dialog status 3)
  (setq *EL:DLUIHost* 'panel)
  (if (and result (not (EL:Get 'capacity-source *EL:PanelDraft*)))
    (setq *EL:PanelDraft* (EL:Put 'capacity-source 'default *EL:PanelDraft*)))
  (if (and result (assoc 'block-ground *EL:PanelDraft*)) (EL:PanelBlockGroundApply))
  (while (and (> dialog 0) (= status 3))
    (if (EL:PanelNewDialog dialog)
      (progn
        (if home (EL:PanelHomeFill)
          (progn
            (EL:LogCall "PANEL_FILL" (list (cons 'panel (EL:Get 'panel result))
              (cons 'circuits (length (EL:Get 'circuits *EL:PanelDraft*)))) 'EL:PanelFill nil)
            (set_tile "p_number" (strcat "配电箱编号：" (EL:PanelNumber *EL:PanelDraft*)))))
        (EL:TrunkButtonDraw)
        (EL:StepLabelsDraw)
        (EL:PanelCircuitColorsDraw *EL:PanelPreviewPalette*)
        (set_tile "p_library_toggle" (if *EL:PanelLibraryExpanded* "收起设备库 <<" "展开设备库 >>"))
        (if *EL:PanelLibraryExpanded* (EL:DLUIPanelBegin *EL:PanelLibrarySnapshot*))
        (EL:MonitorActionTile "p_pick" "(EL:PanelLeave 9)")
        (EL:MonitorActionTile "p_trunk" "(EL:PanelLeave 10)")
        (EL:MonitorActionTile "f_preview" "(EL:PanelLeave 5)")
        (EL:MonitorActionTile "p_library_toggle" "(EL:PanelLibraryToggle)")
        (EL:MonitorActionTile "p_capacity" "(EL:PanelCapacity $value)")
        (EL:MonitorActionTile "p_generate" "(EL:PanelGenerate)")
        (EL:MonitorActionTile "p_diagnostic" "(EL:PanelLeave 17)")
        (if *EL:PanelLibraryExpanded*
          (EL:MonitorActionTile "p_block_library_open" "(EL:PanelLeave 19)"))
        (EL:MonitorActionTile "cancel" "(EL:PanelExit)")
        (if (and (not limit-shown) (setq limit-notice (EL:PanelCircuitLimitText *EL:PanelDraft*)))
          (progn
            (setq limit-shown T)
            (EL:LogEvent "PANEL_CIRCUIT_LIMIT" (list (cons 'actual (length (EL:Get 'circuits *EL:PanelDraft*))) '(maximum . 8)))
            (EL:PanelError limit-notice)))
        (setq *EL:PanelAction* nil status (EL:PerfInput 'start_dialog nil))
        (EL:LogEvent "PANEL_DIALOG_RETURN" (list (cons 'status status) (cons 'action *EL:PanelAction*)))
        (if (= status 21) (setq status 3))
        (if (= status 4)
          (progn
            (princ "\n正在检查系统图块；缺少定义时从随包图块库自动导入。")
            (setq captured (vl-catch-all-apply 'EL:CaptureFixedTemplate (list *EL:PanelConfig*)))
            (EL:ClearPickHighlights)
            (if (and (not (vl-catch-all-error-p captured)) captured)
              (setq *EL:PanelConfig* (EL:Put 'template captured *EL:PanelConfig*)
                *EL:PanelTemplateReady* T status 2)
              (progn (princ "\n模板设置未完成，返回统计面板；当前功率和选择已保留。")
                (setq status 3)))))
        (if (= status 5)
          (progn (EL:AllCircuitColorPreview *EL:PanelDraft*) (setq status 3)))
        (if (= status 17)
          (progn (EL:PanelDiagnosticExportOpen) (setq status 3)))
        (if (= status 19)
          (setq *EL:DLUINotice* (EL:PanelOpenBlockLibrary) status 3))
        (if (= status 20)
          (setq *EL:DLUINotice* (EL:DLOpenCatalog) status 3))
        (if (member status '(13 14 15 16))
          (setq status (EL:PanelLibraryExternal status))))
      (setq status 0)))
  (if (> dialog 0) (unload_dialog dialog))
  (setq *EL:DialogID* nil)
  (cond
    ((= status 12)
      (list (cons 'library-suspended (list (cons 'result *EL:PanelDraft*)
        (cons 'powers *EL:PanelPowers*) (cons 'config *EL:PanelConfig*)
        (cons 'capacity *EL:PanelCapacity*) (cons 'home home)))))
    ((member status '(9 10))
      (if (not home)
        (progn
          (EL:RememberStartPanel (EL:Get 'panel *EL:PanelDraft*) (EL:PanelNumber *EL:PanelDraft*))
          (setq *EL:StartPickResume* (list (cons 'result *EL:PanelDraft*)
            (cons 'powers *EL:PanelPowers*) (cons 'config *EL:PanelConfig*)
            (cons 'capacity *EL:PanelCapacity*)))))
      (list (cons 'pick-panel (if (= status 10) 'trunk T))))
    ((member status '(1 2))
      (list (cons 'result *EL:PanelDraft*) (cons 'powers *EL:PanelPowers*)
        (cons 'config *EL:PanelConfig*) (cons 'capacity *EL:PanelCapacity*)
        (cons 'generate (or (equal *EL:PanelAction* 'generate) (= status 2)))))))

;; Date: 2026-10-10. Green image button with embedded Chinese label; no runtime font/file dependency.
;; Date: 2026-10-13. Labels: 拾取配电箱 / 拾取回路起始端导线; SimSun 12 px.
;; Date: 2026-10-13. Embedded SimSun labels for legacy DCL image buttons.
(defun EL:PickButtonRuns (key)
  (if (equal key "p_pick")
    '((2 0 1) (7 0 1) (40 0 1) (49 0 1) (54 0 1) (2 1 1) (7 1 1) (12 1 6)
    (24 1 7) (32 1 3) (40 1 1) (49 1 4) (54 1 5) (2 2 1) (6 2 1) (8 2 1)
    (13 2 1) (16 2 1) (18 2 4) (26 2 1) (28 2 1) (34 2 1) (36 2 9) (48 2 1)
    (51 2 1) (53 2 1) (56 2 1) (0 3 4) (5 3 1) (9 3 1) (13 3 1) (16 3 1)
    (19 3 1) (21 3 1) (24 3 7) (34 3 1) (36 3 1) (40 3 1) (44 3 1) (50 3 1)
    (2 4 1) (4 4 1) (10 4 1) (13 4 4) (19 4 1) (21 4 1) (24 4 1) (26 4 1)
    (28 4 1) (30 4 1) (34 4 1) (36 4 1) (40 4 1) (44 4 1) (50 4 1) (53 4 6)
    (2 5 1) (5 5 5) (13 5 1) (16 5 1) (19 5 1) (21 5 1) (24 5 1) (26 5 1)
    (28 5 1) (30 5 1) (32 5 3) (36 5 9) (48 5 6) (58 5 1) (2 6 2) (13 6 4)
    (19 6 1) (21 6 1) (24 6 2) (29 6 2) (32 6 1) (36 6 1) (40 6 1) (44 6 1)
    (50 6 1) (53 6 6) (0 7 3) (5 7 5) (13 7 1) (16 7 1) (19 7 1) (21 7 1)
    (24 7 1) (30 7 1) (32 7 1) (36 7 1) (40 7 1) (44 7 1) (49 7 3) (53 7 1)
    (58 7 1) (2 8 1) (5 8 1) (9 8 1) (13 8 1) (16 8 2) (20 8 1) (24 8 7)
    (32 8 1) (36 8 9) (48 8 1) (50 8 1) (52 8 7) (2 9 1) (5 9 1) (9 9 1)
    (12 9 5) (20 9 1) (24 9 1) (30 9 1) (32 9 1) (34 9 1) (36 9 1) (40 9 1)
    (46 9 1) (50 9 1) (53 9 1) (58 9 1) (2 10 1) (5 10 5) (16 10 1) (19 10 1)
    (21 10 1) (24 10 7) (32 10 1) (34 10 1) (40 10 1) (46 10 1) (50 10 1) (53 10 6)
    (1 11 2) (5 11 1) (9 11 1) (16 11 1) (18 11 1) (22 11 1) (24 11 1) (30 11 1)
    (33 11 2) (41 11 6) (50 11 1) (53 11 1) (58 11 1))
    '((2 0 1) (7 0 1) (42 0 1) (51 0 1) (62 0 1) (67 0 1) (72 0 1) (79 0 1)
    (85 0 9) (98 0 1) (103 0 1) (105 0 1) (2 1 1) (7 1 1) (12 1 6) (25 1 10)
    (36 1 4) (42 1 4) (51 1 1) (54 1 4) (62 1 1) (67 1 1) (73 1 1) (76 1 1)
    (79 1 1) (82 1 1) (85 1 1) (93 1 1) (98 1 1) (103 1 1) (106 1 1) (2 2 1)
    (6 2 1) (8 2 1) (13 2 1) (16 2 1) (18 2 4) (25 2 1) (34 2 1) (36 2 1)
    (39 2 1) (41 2 1) (45 2 1) (49 2 4) (57 2 1) (62 2 1) (66 2 1) (76 2 1)
    (79 2 1) (82 2 1) (85 2 9) (97 2 1) (103 2 4) (0 3 4) (5 3 1) (9 3 1)
    (13 3 1) (16 3 1) (19 3 1) (21 3 1) (25 3 1) (34 3 1) (36 3 1) (39 3 2)
    (42 3 1) (44 3 1) (51 3 1) (57 3 1) (60 3 4) (65 3 1) (69 3 1) (72 3 3)
    (76 3 7) (85 3 1) (96 3 1) (99 3 1) (101 3 3) (2 4 1) (4 4 1) (10 4 1)
    (13 4 4) (19 4 1) (21 4 1) (25 4 1) (28 4 4) (34 4 1) (36 4 4) (43 4 1)
    (51 4 1) (54 4 4) (61 4 1) (63 4 1) (65 4 6) (85 4 1) (94 4 1) (96 4 3)
    (103 4 1) (2 5 1) (5 5 5) (13 5 1) (16 5 1) (19 5 1) (21 5 1) (25 5 1)
    (28 5 1) (31 5 1) (34 5 1) (38 5 1) (42 5 1) (44 5 1) (48 5 5) (54 5 1)
    (61 5 1) (63 5 1) (70 5 1) (72 5 1) (74 5 1) (76 5 7) (86 5 9) (98 5 1)
    (103 5 4) (2 6 2) (13 6 4) (19 6 1) (21 6 1) (25 6 1) (28 6 1) (31 6 1)
    (34 6 1) (38 6 1) (40 6 2) (45 6 2) (51 6 1) (54 6 1) (61 6 1) (63 6 1)
    (65 6 5) (72 6 1) (74 6 1) (79 6 1) (97 6 1) (101 6 3) (0 7 3) (5 7 5)
    (13 7 1) (16 7 1) (19 7 1) (21 7 1) (25 7 1) (28 7 4) (34 7 1) (36 7 1)
    (38 7 2) (41 7 5) (49 7 1) (51 7 1) (54 7 1) (58 7 1) (60 7 1) (63 7 1)
    (65 7 1) (69 7 1) (72 7 1) (74 7 1) (76 7 7) (92 7 1) (96 7 4) (103 7 1)
    (105 7 1) (2 8 1) (5 8 1) (9 8 1) (13 8 1) (16 8 2) (20 8 1) (25 8 1)
    (34 8 1) (36 8 1) (38 8 1) (41 8 1) (45 8 1) (49 8 1) (51 8 2) (54 8 1)
    (58 8 1) (61 8 1) (63 8 1) (65 8 1) (69 8 1) (73 8 1) (76 8 1) (78 8 1)
    (80 8 1) (82 8 1) (84 8 11) (103 8 2) (2 9 1) (5 9 1) (9 9 1) (12 9 5)
    (20 9 1) (25 9 1) (34 9 1) (36 9 1) (38 9 1) (41 9 1) (45 9 1) (49 9 1)
    (51 9 1) (55 9 4) (62 9 1) (65 9 1) (69 9 1) (74 9 1) (76 9 1) (78 9 1)
    (80 9 1) (82 9 1) (86 9 1) (92 9 1) (98 9 2) (103 9 1) (106 9 1) (2 10 1)
    (5 10 5) (16 10 1) (19 10 1) (21 10 1) (25 10 10) (36 10 1) (38 10 2) (41 10 5)
    (49 10 3) (61 10 1) (63 10 1) (65 10 5) (72 10 2) (76 10 1) (78 10 1) (80 10 1)
    (82 10 1) (87 10 1) (92 10 1) (96 10 2) (102 10 1) (104 10 1) (106 10 1) (1 11 2)
    (5 11 1) (9 11 1) (16 11 1) (18 11 1) (22 11 1) (25 11 1) (34 11 1) (36 11 2)
    (41 11 1) (45 11 1) (48 11 1) (51 11 8) (60 11 1) (63 11 1) (65 11 1) (69 11 1)
    (76 11 1) (81 11 2) (90 11 3) (100 11 2) (105 11 2))))
(defun EL:TrunkButtonDraw ()
  (EL:GreenPickButton "p_pick" 60)
  (EL:GreenPickButton "p_trunk" 108))
;; Date: 2026-10-10. Raised borders and equal padding for both green buttons.
(defun EL:GreenPickButton (key labelwidth / w h scale ox oy run)
  (setq w (dimx_tile key) h (dimy_tile key)
    scale (max 1 (fix (min (/ (float w) (+ labelwidth 16)) (/ (float h) 20.0))))
    ox (fix (/ (- w (* labelwidth scale)) 2.0)) oy (fix (/ (- h (* 12 scale)) 2.0)))
  (start_image key)
  (fill_image 0 0 w h 0)
  (fill_image 1 1 (- w 2) (- h 2) 8)
  (fill_image 1 1 (- w 3) 2 7)
  (fill_image 1 1 2 (- h 3) 7)
  (fill_image 3 3 (- w 6) (- h 6) 3)
  (foreach run (EL:PickButtonRuns key)
    (if (< (car run) labelwidth)
    (fill_image (+ ox (fix (* (car run) scale))) (+ oy (fix (* (cadr run) scale)))
      (max 1 (- (fix (* (+ (car run) (caddr run)) scale)) (fix (* (car run) scale))))
      (max 1 (- (fix (* (1+ (cadr run)) scale)) (fix (* (cadr run) scale)))) 0)))
  (end_image))

;; Date: 2026-10-11. Number selection is the next step of both model-pick flows.
(defun EL:PickPanelNumber (/ picked data value outcome item done)
  (while (not done)
    (setq outcome (EL:PerfInput 'nentsel (list "\n拾取配电箱编号文字（Enter 使用暂无编号）：")))
    (if (not outcome) (setq value "暂无编号" done T)
      (progn
        (setq picked (car outcome) data (entget picked))
        (if (member (cdr (assoc 0 data)) '("TEXT" "MTEXT" "ATTRIB" "ATTDEF"))
          (progn
            (setq value "")
            (foreach item data (if (= (car item) 3) (setq value (strcat value (cdr item)))))
            (setq value (vl-string-trim " \t\r\n" (strcat value (cdr (assoc 1 data)))))
            (if (or (vl-string-search "\\" value) (vl-string-search "{" value) (vl-string-search "}" value))
              (princ "\n此多行文字包含格式控制，请重新拾取普通编号文字或属性。")
              (setq value (if (= value "") "暂无编号" value) done T)))
          (princ "\n请选择编号文字或属性，或按 Enter 使用暂无编号。")))))
  value)

;; Date: 2026-10-11. Explain rejected generation with circuit and object evidence.
(defun EL:GenerationIssueText (issue / code label)
  (setq code (EL:Get 'code issue)
    label (cond
      ((equal code 'CLOSED_CIRCUIT) "检测到闭合连接，请核对是否重复连接或误接")
      ((equal code 'AMBIGUOUS_CONTACT) "接触位置存在多种连接可能")
      ((equal code 'CIRCUIT_OWNERSHIP_CONFLICT) "多条回路共用对象")
      ((equal code 'OTHER_PANEL) "连接到其他配电箱")
      ((equal code 'UNKNOWN_ROLE) "对象用途未明确")
      ((equal code 'ABNORMAL_BRANCH) "分支连接异常")
      ((equal code 'JUNCTION_INCOMPLETE) "接线盒只有一个有效接入导线，请核对盒后线路")
      ((equal code 'POWER_MISSING_OR_INVALID) "设备功率缺失或无效")
      ((equal code 'POWER_OVERFLOW) "功率计算超出范围")
      ((equal code 'POWER_OVER_LIMIT) "回路功率超过172W")
      ((equal code 'DEVICE_OWNERSHIP_CONFLICT) "设备被多个回路共同识别")
      ((equal code 'DEVICE_LIBRARY_UNKNOWN) "设备功率未填写；请在图例表填写单个功率")
      ((equal code 'DEVICE_LIBRARY_UNAVAILABLE) "设备库读取失败；原文件保留，请修复后重新统计")
      (T (strcat "连接或几何检查未通过：" (vl-prin1-to-string code)))))
  (strcat label "；对象：" (vl-prin1-to-string (EL:Get 'object issue))
    "；详情：" (vl-prin1-to-string (EL:Get 'detail issue))))
;; Date: 2026-10-12. Aggregate the two power validators by device name across circuits.
(defun EL:GenerationMissing (result / rows circuit issue index ids identity id block name key row)
  (setq index 0)
  (foreach circuit (EL:Get 'circuits result)
    (setq index (1+ index))
    (foreach issue (append (EL:Get 'issues circuit) (EL:Get 'power-issues circuit))
      (if (member (EL:Get 'code issue) '(POWER_MISSING_OR_INVALID DEVICE_LIBRARY_UNKNOWN))
        (progn
          (setq ids (EL:Get 'object issue) identity (EL:Get 'detail issue))
          (if (not (listp ids)) (setq ids (list ids)))
          (foreach id ids
            (setq block (EL:By 'id id (EL:Get 'blocks (EL:Get 'snapshot result)))
              name (cond ((EL:Get 'name block)) ((equal (type identity) 'STR) identity)
                ((and (listp identity) (equal (type (car identity)) 'STR)) (car identity))
                ((equal (type id) 'STR) id) (T "未命名设备"))
              key (EL:DLNameKey name) row (EL:By 'key key rows))
            (if (not row) (setq row (list (cons 'key key) (cons 'name name) '(ids) '(circuits)) rows (append rows (list row))))
            (setq rows (subst (EL:Put 'ids (EL:Unique (cons id (EL:Get 'ids row)))
              (EL:Put 'circuits (EL:Unique (append (EL:Get 'circuits row) (list (itoa index)))) row)) row rows))))))) rows)
(defun EL:GenerationProblems (result / lines circuit issue index problems row missing)
  (setq index 0)
  (setq missing (EL:GenerationMissing result))
  (foreach row missing
    (setq lines (append lines (list (strcat (EL:Get 'name row) "：请填写或核对单个功率；"
      (itoa (length (EL:Get 'ids row))) " 个设备，回路 " (EL:DLAliasText (EL:Get 'circuits row)) "。")))))
  (foreach circuit (EL:Get 'circuits result)
    (setq index (1+ index) problems (EL:Unique (append (EL:Get 'issues circuit) (EL:Get 'power-issues circuit))))
    (foreach issue problems
      (if (not (member (EL:Get 'code issue) '(POWER_MISSING_OR_INVALID DEVICE_LIBRARY_UNKNOWN)))
        (setq lines (append lines (list (strcat "回路" (itoa index) "：" (EL:GenerationIssueText issue)))))))
    (if (and (not problems) (not (EL:Get 'power-complete circuit)))
      (setq lines (append lines (list (strcat "回路" (itoa index) "：连接或功率核对未完成，请查看全部回路。"))))))
  (foreach issue (EL:Get 'issues (EL:Get 'snapshot result))
    (setq lines (append lines (list (strcat "图面：" (EL:GenerationIssueText issue))))))
  (if (EL:Get 'box-total-overflow result) (setq lines (append lines '("整箱功率计算超出范围。"))))
  (if lines lines '("识别状态未完成，请重新统计并查看全部回路；详细状态已写入日志。")))
(defun EL:PanelGenerationBlocked (result / lines line message compact index missing)
  (setq lines (EL:GenerationProblems result) message "不能生成，原因如下：")
  (setq missing (EL:GenerationMissing result))
  (if missing (setq message (strcat "尚有 " (itoa (length missing)) " 种设备需要填写或核对单个功率。"
    "\n请运行 ELDEVLIB 或点击“打开独立设备库”补齐资料：")))
  (setq compact message index 0)
  (foreach line lines (setq message (strcat message "\n" line)))
  (foreach line lines
    (if (< index 10) (setq compact (strcat compact "\n" line))) (setq index (1+ index)))
  (if (> index 10) (setq compact (strcat compact "\n另有 " (itoa (- index 10)) " 项，完整详情已写入诊断日志。")))
  (EL:LogEvent "GENERATION_BLOCKED" (list (cons 'panel (EL:Get 'panel result))
    (cons 'reasons lines) (cons 'circuits (EL:Get 'circuits result))))
  (EL:PanelText "p_error" (car lines))
  (princ (strcat "\n" message))
  (alert (strcat compact (if missing "\n补齐设备库资料后返回本面板重新核对。" "")
    "\n可保存草稿；连接问题请用“查看全部回路”核对。")))

;; Date: 2026-10-15. ACI 1 draws only the step numbers, on the dialog background.
(defun EL:RedStepDraw (key index / w h scale ox oy run)
  (setq w (dimx_tile key) h (dimy_tile key)
    scale (max 1 (fix (min (/ (float w) 56.0) (/ (float h) 14.0))))
    ox 0 oy (fix (/ (- h (* 14 scale)) 2.0)))
  (start_image key)
  (fill_image 0 0 w h -15)
  (foreach run (EL:StepLabelRuns index)
    (fill_image (+ ox (* (car run) scale)) (+ oy (* (cadr run) scale))
      (* (caddr run) scale) scale 1))
  (end_image))
(defun EL:StepLabelsDraw (/ index)
  (setq index 1)
  (repeat 4 (EL:RedStepDraw (strcat "p_step" (itoa index)) index) (setq index (1+ index))))

;; BEGIN GENERATED RED STEP LABELS
;; Date: 2026-10-15. SimSun 14 px, 56 x 14; runtime has no font/file dependency.
(defun EL:StepLabelRuns (index)
  (nth (1- index) '
(
  ; 第一步：
  (    (2 0 1) (8 0 1) (34 0 1) (2 1 4) (8 1 5) (30 1 1) (34 1 1) (1 2 1)
    (3 2 1) (7 2 1) (10 2 1) (30 2 1) (34 2 6) (0 3 1) (4 3 1) (6 3 1)
    (11 3 1) (30 3 1) (34 3 1) (30 4 1) (34 4 1) (1 5 10) (28 5 13) (6 6 1)
    (10 6 1) (14 6 13) (45 6 2) (1 7 10) (31 7 1) (34 7 1) (45 7 2) (1 8 1)
    (6 8 1) (30 8 1) (34 8 1) (38 8 1) (1 9 11) (29 9 1) (34 9 1) (37 9 1)
    (4 10 1) (6 10 1) (11 10 1) (34 10 1) (36 10 1) (45 10 2) (2 11 2) (6 11 1)
    (11 11 1) (34 11 2) (45 11 2) (0 12 2) (6 12 1) (9 12 2) (31 12 3) (6 13 1)
    (28 13 3))
  ; 第二步：
  (    (2 0 1) (8 0 1) (34 0 1) (2 1 4) (8 1 5) (30 1 1) (34 1 1) (1 2 1)
    (3 2 1) (7 2 1) (10 2 1) (15 2 11) (30 2 1) (34 2 6) (0 3 1) (4 3 1)
    (6 3 1) (11 3 1) (30 3 1) (34 3 1) (30 4 1) (34 4 1) (1 5 10) (28 5 13)
    (6 6 1) (10 6 1) (45 6 2) (1 7 10) (31 7 1) (34 7 1) (45 7 2) (1 8 1)
    (6 8 1) (30 8 1) (34 8 1) (38 8 1) (1 9 11) (29 9 1) (34 9 1) (37 9 1)
    (4 10 1) (6 10 1) (11 10 1) (34 10 1) (36 10 1) (45 10 2) (2 11 2) (6 11 1)
    (11 11 1) (34 11 2) (45 11 2) (0 12 2) (6 12 1) (9 12 2) (14 12 13) (31 12 3)
    (6 13 1) (28 13 3))
  ; 第三步：
  (    (2 0 1) (8 0 1) (34 0 1) (2 1 4) (8 1 5) (15 1 11) (30 1 1) (34 1 1)
    (1 2 1) (3 2 1) (7 2 1) (10 2 1) (30 2 1) (34 2 6) (0 3 1) (4 3 1)
    (6 3 1) (11 3 1) (30 3 1) (34 3 1) (30 4 1) (34 4 1) (1 5 10) (28 5 13)
    (6 6 1) (10 6 1) (45 6 2) (1 7 10) (16 7 9) (31 7 1) (34 7 1) (45 7 2)
    (1 8 1) (6 8 1) (30 8 1) (34 8 1) (38 8 1) (1 9 11) (29 9 1) (34 9 1)
    (37 9 1) (4 10 1) (6 10 1) (11 10 1) (34 10 1) (36 10 1) (45 10 2) (2 11 2)
    (6 11 1) (11 11 1) (34 11 2) (45 11 2) (0 12 2) (6 12 1) (9 12 2) (31 12 3)
    (6 13 1) (14 13 13) (28 13 3))
  ; 第四步：
  (    (2 0 1) (8 0 1) (34 0 1) (2 1 4) (8 1 5) (15 1 12) (30 1 1) (34 1 1)
    (1 2 1) (3 2 1) (7 2 1) (10 2 1) (15 2 1) (19 2 1) (22 2 1) (26 2 1)
    (30 2 1) (34 2 6) (0 3 1) (4 3 1) (6 3 1) (11 3 1) (15 3 1) (19 3 1)
    (22 3 1) (26 3 1) (30 3 1) (34 3 1) (15 4 1) (19 4 1) (22 4 1) (26 4 1)
    (30 4 1) (34 4 1) (1 5 10) (15 5 1) (19 5 1) (22 5 1) (26 5 1) (28 5 13)
    (6 6 1) (10 6 1) (15 6 1) (19 6 1) (22 6 1) (26 6 1) (45 6 2) (1 7 10)
    (15 7 1) (19 7 1) (22 7 1) (26 7 1) (31 7 1) (34 7 1) (45 7 2) (1 8 1)
    (6 8 1) (15 8 1) (19 8 1) (22 8 1) (26 8 1) (30 8 1) (34 8 1) (38 8 1)
    (1 9 11) (15 9 1) (18 9 1) (23 9 4) (29 9 1) (34 9 1) (37 9 1) (4 10 1)
    (6 10 1) (11 10 1) (15 10 1) (17 10 1) (26 10 1) (34 10 1) (36 10 1) (45 10 2)
    (2 11 2) (6 11 1) (11 11 1) (15 11 1) (26 11 1) (34 11 2) (45 11 2) (0 12 2)
    (6 12 1) (9 12 2) (15 12 12) (31 12 3) (6 13 1) (15 13 1) (26 13 1) (28 13 3))
)))
;; END GENERATED RED STEP LABELS

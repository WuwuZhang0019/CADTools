;; Date: 2026-10-15. Locate the saved parameters of the currently edited library.
(defun EL:DLOpenCatalog (/ root path present outcome)
  (setq root (EL:Get 'root (EL:Get 'snapshot *EL:DLUIState*)))
  (if (and root (vl-file-directory-p root))
    (progn
      (setq path (strcat (EL:NormalizeRoot root) "catalog.eld") present (findfile path)
        outcome (vl-catch-all-apply 'startapp
          (list "explorer.exe" (strcat (if present "/select,\"" "\"")
            (vl-string-translate "/" "\\" (if present path root)) "\""))))
      (cond
        ((or (not outcome) (vl-catch-all-error-p outcome))
          "无法打开设备库文件夹，请按上方目录查找 catalog.eld。")
        (present "已选中 catalog.eld；确认自动保存成功后，可发送此文件作为默认功率来源。")
        (T "已打开设备库目录；catalog.eld 尚未生成，修改设备资料并自动保存成功后会生成。")))
    "设备库目录不存在，请检查当前库目录。"))
;; Date: 2026-10-11. One-window CRUD; draft state survives picking and Escape.
(defun EL:DLStrip (entry)
  (vl-remove-if '(lambda (p) (member (car p) '(captured watts-text aliases-text keep-old-name panel-name))) entry))
(defun EL:DLAliases (text / index name out)
  (while (setq index (vl-string-search ";" text))
    (setq name (substr text 1 index) text (substr text (+ index 2)))
    (if (/= name "") (setq out (cons name out))))
  (if (/= text "") (setq out (cons text out))) (reverse out))
(defun EL:DLAliasText (names / text name)
  (setq text "") (foreach name names (setq text (strcat text (if (= text "") "" ";") name))) text)
(defun EL:DLUIDraft ()
  (EL:Get (EL:Get 'selected *EL:DLUIState*) (EL:Get 'drafts *EL:DLUIState*)))
(defun EL:DLUIEntry ()
  (cond ((EL:DLUIDraft)) (T (EL:By 'device-id (EL:Get 'selected *EL:DLUIState*)
    (EL:Get 'devices (EL:Get 'catalog (EL:Get 'snapshot *EL:DLUIState*)))))))
(defun EL:DLUISetDraft (entry)
  (setq *EL:DLUIState* (EL:Put 'selected (EL:Get 'device-id entry)
    (EL:Put 'drafts (EL:Put (EL:Get 'device-id entry) entry (EL:Get 'drafts *EL:DLUIState*)) *EL:DLUIState*))) entry)
(defun EL:DLUIForget (identity / draft)
  (if (and (setq draft (EL:Get identity (EL:Get 'drafts *EL:DLUIState*))) (EL:Get 'captured draft))
    (EL:DLCaptureCleanup (EL:Get 'captured draft)))
  (setq *EL:DLUIState* (EL:Put 'verify-pending (vl-remove identity (EL:Get 'verify-pending *EL:DLUIState*))
    (EL:Put 'drafts (vl-remove-if '(lambda (p) (equal (car p) identity))
      (EL:Get 'drafts *EL:DLUIState*)) *EL:DLUIState*))))
(defun EL:DLUIStore (/ entry key ground)
  (if (setq entry (EL:DLUIEntry))
    (progn
      (foreach key '((block-name . "dl_block") (display . "dl_display") (watts-text . "dl_watts") (aliases-text . "dl_aliases"))
        (setq entry (EL:Put (car key) (get_tile (cdr key)) entry)))
      (setq ground (atoi (get_tile "dl_ground")) entry (EL:Put 'ground-confirmed (> ground 0)
        (EL:Put 'is-ground (= ground 2) (EL:Put 'zero-confirmed (equal (get_tile "dl_zero") "1")
          (EL:Put 'active (equal (get_tile "dl_active") "1") entry)))))
      (setq entry (EL:Put 'keep-old-name (equal (get_tile "dl_keep_old") "1") entry))
      (EL:DLUISetDraft entry)))
  (EL:DLUIAutoSave))
(defun EL:DLUIRows (/ rows pair old)
  (setq rows (EL:Get 'devices (EL:Get 'catalog (EL:Get 'snapshot *EL:DLUIState*))))
  (foreach pair (EL:Get 'drafts *EL:DLUIState*)
    (setq old (EL:By 'device-id (car pair) rows) rows (if old (subst (cdr pair) old rows) (append rows (list (cdr pair))))))
  (EL:DLSearch (list (cons 'devices rows)) (EL:Get 'query *EL:DLUIState*) (EL:Get 'deleted *EL:DLUIState*)))
(defun EL:DLUIText (key text)
  (set_tile key text))
(defun EL:DLUIStatus (text)
  (setq *EL:DLUINotice* text)
  (EL:DLUIText "dl_status" text))
(defun EL:DLUIAssetKey (entry snapshot / root dwg slide dwgtime slidetime)
  ;; Date: 2026-10-15. Cache only this editor's validated, unchanged asset version.
  (if (and (setq root (EL:Get 'root snapshot)) (EL:DLEntryAssets entry)
      (findfile (setq dwg (strcat root (EL:Get 'block-file entry))))
      (findfile (setq slide (strcat root (EL:Get 'legend-file entry))))
      (setq dwgtime (vl-file-systime dwg)) (setq slidetime (vl-file-systime slide)))
    (list root (EL:Get 'library-id (EL:Get 'catalog snapshot))
      (mapcar '(lambda (key) (EL:Get key entry))
        '(device-id asset-revision block-file legend-file legend-size legend-checksum))
      (vl-file-size dwg) dwgtime (vl-file-size slide) slidetime)))
(defun EL:DLUIAsset (entry snapshot / key cached preview checked)
  (setq key (EL:DLUIAssetKey entry snapshot))
  (if (and key (setq cached (assoc key *EL:DLUIAssets*))) (cdr cached)
    (progn
      (setq preview (EL:DLLegend entry snapshot)
        checked (and preview (EL:Get 'root snapshot)
          (EL:DLDWGValid (strcat (EL:Get 'root snapshot) (EL:Get 'block-file entry)))))
      (if (and key checked) (setq *EL:DLUIAssets* (cons (cons key (list preview checked)) *EL:DLUIAssets*)))
      (list preview checked))))
(defun EL:DLUIFields (/ entry preview ground key size shown)
  (setq entry (EL:DLUIEntry) ground (if (EL:Get 'ground-confirmed entry) (if (EL:Get 'is-ground entry) "2" "1") "0"))
  (foreach key '((block-name . "dl_block") (display . "dl_display")) (set_tile (cdr key) (cond ((EL:Get (car key) entry)) (T ""))))
  (set_tile "dl_aliases" (cond ((EL:Get 'aliases-text entry)) (T (EL:DLAliasText (EL:Get 'aliases entry)))))
  (set_tile "dl_watts" (cond ((EL:Get 'watts-text entry)) ((numberp (EL:Get 'watts entry)) (itoa (EL:Get 'watts entry))) (T "")))
  (set_tile "dl_ground" ground) (set_tile "dl_zero" (if (EL:Get 'zero-confirmed entry) "1" "0"))
  (set_tile "dl_active" (if (or (EL:Get 'active entry) (equal (EL:Get 'revision entry) 0)) "1" "0"))
  (set_tile "dl_keep_old" (if (or (not (assoc 'keep-old-name entry)) (EL:Get 'keep-old-name entry)) "1" "0"))
  (if (EL:Get 'captured entry)
    (if (setq size (EL:DLSLDSize (EL:Get 'slide (EL:Get 'captured entry))))
      (setq preview (list (EL:Get 'slide (EL:Get 'captured entry)) size)))
    (setq preview (car (EL:DLUIAsset entry (EL:Get 'snapshot *EL:DLUIState*)))))
  (setq shown (EL:ThumbDraw "dl_image" preview))
  (EL:DLUIText "dl_asset" (cond ((not entry) "点击新增或选择设备")
    ((and shown (EL:Get 'captured entry)) "新图形已预览，资料将自动保存")
    (shown "已保存图块图形和标准图例")
    (preview "图例显示失败，请修复或重新拾取图形")
    ((> (EL:Get 'asset-revision entry) 0) "图例缺失或损坏，请修复或重新拾取图形")
    (T "未登记图形，请从 CAD 拾取设备图块")))
  (foreach key '("dl_block" "dl_display" "dl_watts" "dl_aliases" "dl_zero" "dl_ground" "dl_active" "dl_keep_old" "dl_save")
    (mode_tile key (if (and entry (not (equal (EL:Get 'status entry) 'deleted))) 0 1)))
  ;; A pending worker only locks graph-changing actions; existing parameters remain editable.
  (foreach key '("dl_pick" "dl_new" "dl_import" "dl_directory")
    (mode_tile key (if *EL:DLCaptureJob* 1 0)))
  (mode_tile "dl_delete" (if (and entry (not (equal (EL:Get 'status entry) 'deleted))) 0 1))
  (mode_tile "dl_export" (if (EL:Get 'snapshot *EL:DLUIState*) 0 1))
  (mode_tile "dl_restore" (if (and entry (equal (EL:Get 'status entry) 'deleted)) 0 1)))
(defun EL:DLUIRowText (entry)
  (strcat (EL:Get 'block-name entry) " / " (EL:Get 'display entry) " / "
    (cond ((equal (EL:Get 'status entry) 'deleted) "已删除") ((EL:Get 'active entry) "启用") (T "草稿或停用"))))
(defun EL:DLUIRowUpdate (entry / old index)
  ;; Keep visible indices and scroll position; parameter edits never rebuild the list.
  (if (setq old (EL:By 'device-id (EL:Get 'device-id entry) *EL:DLUIRows*))
    (progn
      (if (not (equal (EL:DLUIRowText old) (EL:DLUIRowText entry)))
        (progn (setq index (vl-position old *EL:DLUIRows*))
          (start_list "dl_rows" 1 index) (add_list (EL:DLUIRowText entry)) (end_list)))
      (setq *EL:DLUIRows* (subst entry old *EL:DLUIRows*)))))
(defun EL:DLUIFill (/ entry index selected snapshot)
  (setq *EL:DLUIAssets* nil *EL:DLUIRows* (EL:DLUIRows) index 0 selected nil snapshot (EL:Get 'snapshot *EL:DLUIState*))
  (start_list "dl_rows")
  (foreach entry *EL:DLUIRows*
    (if (equal (EL:Get 'device-id entry) (EL:Get 'selected *EL:DLUIState*)) (setq selected index))
    (add_list (EL:DLUIRowText entry))
    (setq index (1+ index)))
  (end_list)
  ;; A search can hide the current draft without discarding it.
  (if selected (set_tile "dl_rows" (itoa selected)))
  (set_tile "dl_query" (EL:Get 'query *EL:DLUIState*)) (set_tile "dl_deleted" (if (EL:Get 'deleted *EL:DLUIState*) "1" "0"))
  (set_tile "dl_root" (strcat "设备库：" (EL:Get 'root snapshot) "  版本 " (itoa (EL:Get 'revision (EL:Get 'catalog snapshot)))))
  (EL:DLUIFields))
(defun EL:DLUISelect (value / entry previous)
  (setq entry (nth (atoi value) *EL:DLUIRows*) previous (EL:Get 'selected *EL:DLUIState*))
  (EL:DLUIStore)
  (if (and entry (not (equal previous (EL:Get 'device-id entry))))
    (progn (setq *EL:DLUIState* (EL:Put 'selected (EL:Get 'device-id entry) *EL:DLUIState*)) (EL:DLUIFields))))
(defun EL:DLUINew (/ catalog row serial)
  (EL:DLUIStore) (setq catalog (EL:Get 'catalog (EL:Get 'snapshot *EL:DLUIState*)) row (EL:DLEntryNew catalog "新设备") serial (EL:Get 'next-id catalog))
  (while (EL:Get (EL:Get 'device-id row) (EL:Get 'drafts *EL:DLUIState*))
    (setq serial (1+ serial) row (EL:DLEntryNew (EL:Put 'next-id serial catalog) "新设备")))
  (EL:DLUISetDraft row) (setq *EL:DLUIState* (EL:Put 'query "" *EL:DLUIState*)) (EL:DLUIFill)
  (EL:DLUIStatus "填写设备资料并拾取图形；离开输入框后自动保存，缺资料时保存为草稿。"))
(defun EL:DLUIRefresh (/ snapshot)
  (EL:DLUIStore)
  (if (setq snapshot (EL:DLSnapshotLoad (EL:Get 'root (EL:Get 'snapshot *EL:DLUIState*))))
    (progn (setq *EL:DLUIState* (EL:Put 'snapshot snapshot *EL:DLUIState*)) (EL:DLUIFill)
      (EL:DLUIStatus "列表已刷新，未保存输入保留；版本冲突时可重载选中项。")) (EL:DLUIStatus *EL:DLError*)))
(defun EL:DLUIReload ()
  (EL:DLUIRefresh) (EL:DLUIForget (EL:Get 'selected *EL:DLUIState*)) (EL:DLUIFill)
  (EL:DLUIStatus "选中项已重新载入已保存资料。"))
(defun EL:DLUIToEntry (draft / entry raw watts captured old names)
  (setq raw (EL:Get 'watts-text draft) watts (if raw (EL:ParseWatts raw) (EL:Get 'watts draft)))
  (if (and raw (/= raw "") (not (numberp watts))) (EL:DLFail "功率请输入非负整数 W；输入已保留。")
    (progn (setq entry (EL:Put 'watts watts (EL:DLStrip draft)))
      (if (assoc 'aliases-text draft) (setq entry (EL:Put 'aliases (EL:DLAliases (EL:Get 'aliases-text draft)) entry)))
      (setq old (EL:By 'device-id (EL:Get 'device-id entry)
        (EL:Get 'devices (EL:Get 'catalog (EL:Get 'snapshot *EL:DLUIState*)))))
      (if (and old (or (not (assoc 'keep-old-name draft)) (EL:Get 'keep-old-name draft))
          (not (equal (EL:DLNameKey (EL:Get 'block-name old)) (EL:DLNameKey (EL:Get 'block-name entry)))))
        (progn (setq names (mapcar 'EL:DLNameKey (EL:Get 'aliases entry)))
          (if (not (member (EL:DLNameKey (EL:Get 'block-name old)) names))
            (setq entry (EL:Put 'aliases (append (EL:Get 'aliases entry) (list (EL:Get 'block-name old))) entry)))))
      (if (setq captured (EL:Get 'captured draft))
        (setq entry (EL:DLAssetInstall (EL:Get 'snapshot *EL:DLUIState*) entry (EL:Get 'dwg captured) (EL:Get 'slide captured))))
      (if (EL:DLEntryReady entry) (EL:Put 'status 'ready entry) (EL:Put 'active nil (EL:Put 'status 'draft entry))))))
(defun EL:DLUIAssetReady (entry snapshot)
  (and (EL:DLEntryReady entry) (cadr (EL:DLUIAsset entry snapshot))))
(defun EL:DLUISaveWork (/ snapshot draft entry old candidate loaded converted)
  ;; Date: 2026-10-15. Persist edits without refilling controls or moving focus.
  (setq snapshot (EL:Get 'snapshot *EL:DLUIState*) draft (EL:DLUIEntry) *EL:DLError* nil
    old (EL:By 'device-id (EL:Get 'device-id draft) (EL:Get 'devices (EL:Get 'catalog snapshot))))
  (cond
    ((or (not draft) (equal (EL:Get 'status draft) 'deleted)) T)
    ((and (not (EL:Get 'captured draft))
        (setq converted T entry (EL:DLUIToEntry draft)) (equal entry old))
      ;; Date: 2026-10-16. An explicit save also verifies already-autosaved values on disk.
      (if (or (not (or *EL:DLUIManualSave*
            (member (EL:Get 'device-id draft) (EL:Get 'verify-pending *EL:DLUIState*))))
          (EL:DLSnapshotCurrent snapshot))
        (progn (EL:DLUIForget (EL:Get 'device-id draft)) T)
        (progn
          (setq *EL:DLUIState* (EL:Put 'verify-pending (EL:Unique (cons (EL:Get 'device-id draft)
            (EL:Get 'verify-pending *EL:DLUIState*))) *EL:DLUIState*))
          (EL:DLUIStatus "保存核对未通过：文件已变化、被占用或无法读取；输入保留，请刷新后重试。") nil)))
    ((or (findfile (strcat (EL:Get 'root snapshot) ".write-lock"))
        (and (EL:Get 'captured draft) (not (EL:DLSnapshotCurrent snapshot))))
      (EL:DLUIStatus "自动保存未完成：设备库已变化或正在被占用，请刷新后重试；当前输入保留。") nil)
    ((and (or entry (and (not converted) (setq entry (EL:DLUIToEntry draft))))
      (or (not (EL:DLEntryReady entry)) (EL:DLUIAssetReady entry snapshot)
        (EL:DLFail "图形或图例缺失、损坏，未发布；请拾取图形或修复图例，输入已保留。"))
      (setq candidate (EL:DLUpsert (EL:Get 'catalog snapshot) entry)) (EL:DLCommit snapshot candidate))
      (EL:DLUIForget (EL:Get 'device-id draft))
      ;; DLCommit already checked the original under lock and read back this exact catalog.
      (setq loaded (EL:Put 'index (EL:DLIndex candidate)
        (EL:Put 'catalog candidate (EL:Put 'raw (vl-prin1-to-string candidate) (EL:Put 'present T snapshot)))))
      (setq *EL:DLUIState* (EL:Put 'snapshot loaded *EL:DLUIState*) *EL:DLCache* nil *EL:DLError* nil)
      ;; A rename can add the old block name; later field callbacks must keep that alias.
      (set_tile "dl_aliases" (EL:DLAliasText (EL:Get 'aliases (EL:By 'device-id
        (EL:Get 'device-id draft) (EL:Get 'devices candidate)))))
      (set_tile "dl_root" (strcat "设备库：" (EL:Get 'root loaded) "  版本 " (itoa (EL:Get 'revision candidate))))
      (EL:DLUIRowUpdate (EL:By 'device-id (EL:Get 'device-id draft) (EL:Get 'devices candidate)))
      (EL:DLUIStatus (if (equal (EL:Get 'status entry) 'ready) "设备资料已自动保存。"
        "设备资料已自动保存为草稿；补齐图形、功率和地面资料后可启用。")) T)
    (T (EL:DLUIStatus (strcat "自动保存未完成：" (cond (*EL:DLError*) (T "保存失败，输入已保留。")))) nil)))
(defun EL:DLUIAutoSave (/ saved previous)
  (setq previous (EL:Get 'snapshot *EL:DLUIState*) saved (EL:DLUISafe 'EL:DLUISaveWork))
  (if (and saved (equal *EL:DLUIHost* 'panel)
      (not (equal previous (EL:Get 'snapshot *EL:DLUIState*))) (EL:PanelLibraryReconcile)) (EL:PanelFill)) saved)
(defun EL:DLUISave (/ entry *EL:DLUIManualSave*)
  ;; Date: 2026-10-16. Read the controls even if their focus-loss callback did not run.
  (setq entry (EL:DLUIEntry) *EL:DLUIManualSave* T)
  (if (and entry (not (equal (EL:Get 'status entry) 'deleted)))
    (progn
      (setq *EL:DLUIState* (EL:Put 'verify-pending (EL:Unique (cons (EL:Get 'device-id entry)
        (EL:Get 'verify-pending *EL:DLUIState*))) *EL:DLUIState*))
      (if (EL:DLUIStore)
        (progn
          (setq entry (EL:DLUIEntry))
          (EL:DLUIStatus (strcat "已保存并核对：" (EL:Get 'display entry) "，"
            (if (numberp (EL:Get 'watts entry)) (strcat (itoa (EL:Get 'watts entry)) " W。")
              "功率未填写（草稿）。"))) T)))
    (progn (EL:DLUIStatus "请选择未删除的设备后保存。") nil)))
(defun EL:DLUIAutoBind (/ key)
  (foreach key '("dl_block" "dl_aliases" "dl_keep_old" "dl_display" "dl_watts" "dl_zero" "dl_ground" "dl_active")
    (EL:MonitorActionTile key "(EL:DLUIStore)"))
  (EL:MonitorActionTile "dl_save" "(EL:DLUISafe 'EL:DLUISave)"))
(defun EL:DLUIFlush (/ selected pair failed notice)
  ;; Closing/exporting also retries older drafts; failure stays visible in this editor.
  (setq selected (EL:Get 'selected *EL:DLUIState*))
  (if (not (EL:DLUIStore)) (setq failed selected))
  (foreach pair (EL:Get 'drafts *EL:DLUIState*)
    (if (not failed)
      (progn
        (setq *EL:DLUIState* (EL:Put 'selected (car pair) *EL:DLUIState*))
        (if (not (EL:DLUIAutoSave)) (setq failed (car pair))))))
  (setq notice *EL:DLUINotice*
    *EL:DLUIState* (EL:Put 'selected (if failed failed selected) *EL:DLUIState*))
  (if failed (progn (EL:DLUIFill) (EL:DLUIStatus notice))) (not failed))
(defun EL:DLUILeave (status)
  (if (EL:DLUIFlush)
    (if (equal *EL:DLUIHost* 'panel) (EL:PanelClose status) (done_dialog status))))
(defun EL:DLUISafe (function / result checkpoint)
  (setq checkpoint *EL:PerfPending* result (vl-catch-all-apply function nil))
  (if (vl-catch-all-error-p result)
    (progn (EL:PerfUnwind checkpoint)
      (EL:DLUIStatus (strcat "操作未完成，输入已保留：" (vl-catch-all-error-message result)))
      (setq result nil))) result)
(defun EL:DLUIRestore (snapshot identity / entry)
  (setq entry (EL:By 'device-id identity (EL:Get 'devices (EL:Get 'catalog snapshot))))
  (if (and entry (EL:DLEntryReady entry) (not (EL:DLUIAssetReady entry snapshot)))
    (EL:DLUpsert (EL:Get 'catalog snapshot) (EL:Put 'active nil (EL:Put 'status 'draft entry)))
    (EL:DLRestore (EL:Get 'catalog snapshot) identity)))
(defun EL:DLUIChangeStatus (deleted / snapshot entry candidate)
  (EL:DLUIStore) (setq snapshot (EL:Get 'snapshot *EL:DLUIState*) entry (EL:DLUIEntry))
  (if (and entry (= (EL:Get 'revision entry) 0) deleted)
    (progn (EL:DLUIForget (EL:Get 'device-id entry)) (setq *EL:DLUIState* (EL:Put 'selected nil *EL:DLUIState*)) (EL:DLUIFill))
    (if (and entry (setq candidate (if deleted (EL:DLDelete (EL:Get 'catalog snapshot) (EL:Get 'device-id entry))
        (EL:DLUIRestore snapshot (EL:Get 'device-id entry)))) (EL:DLCommit snapshot candidate))
      (progn (EL:DLUIForget (EL:Get 'device-id entry))
        (setq *EL:DLUIState* (EL:Put 'snapshot (EL:DLSnapshotLoad (EL:Get 'root snapshot)) *EL:DLUIState*))
        (EL:DLUIFill) (EL:DLUIStatus (if deleted "已删除，历史图形保留；勾选显示已删除设备可恢复。"
          (if (equal (EL:Get 'status (EL:DLUIEntry)) 'draft) "已恢复为草稿；请补齐或修复图形资料后保存启用。" "设备已恢复。"))))
      (EL:DLUIStatus (cond (*EL:DLError*) (T "未操作，资料保留。"))))))
(defun EL:DLUIQuery (value deleted)
  (EL:DLUIStore) (setq *EL:DLUIState* (EL:Put 'deleted deleted (EL:Put 'query value *EL:DLUIState*))) (EL:DLUIFill))
(defun EL:DLUICaptureEntry (entry / snapshot origin draft saved)
  ;; Date: 2026-10-15. Both picking and repair callbacks keep newer parameter edits.
  (setq snapshot (EL:Get 'snapshot *EL:DLUIState*) origin (EL:Get 'snapshot (EL:Get 'captured entry)))
  (if (and (equal (EL:Get 'root snapshot) (EL:Get 'root origin))
      (equal (EL:Get 'library-id (EL:Get 'catalog snapshot)) (EL:Get 'library-id (EL:Get 'catalog origin))))
    (progn
      (setq draft (EL:Get (EL:Get 'device-id entry) (EL:Get 'drafts *EL:DLUIState*)))
      (if (and (not draft)
          (setq saved (EL:By 'device-id (EL:Get 'device-id entry) (EL:Get 'devices (EL:Get 'catalog snapshot))))
          (or (> (EL:Get 'revision entry) 0)
            (member (EL:DLNameKey (EL:Get 'block-name entry)) (mapcar 'EL:DLNameKey (EL:DLEntryNames saved)))))
        (setq draft saved))))
  (if draft (EL:Put 'captured (EL:Get 'captured entry) draft) entry))
(defun EL:DLUIResume (entry / continuation)
  (if entry (EL:DLUISetDraft (EL:DLUICaptureEntry entry)))
  (setq *EL:DLContinue* nil continuation
    (if (equal *EL:DLUIHost* 'panel) T (EL:DLUIRun)))
  (if (and (not (equal continuation 'suspended)) *EL:DLParentContinue*) (apply *EL:DLParentContinue* nil)))
(defun EL:DLUIBusinessFields (entry)
  (vl-remove-if '(lambda (p) (member (car p) '(revision asset-revision block-file legend-file legend-size legend-checksum))) entry))
(defun EL:DLUIAdoptSnapshot (snapshot / catalog oldcatalog drafts selected pair draft base previous identity key)
  ;; Date: 2026-10-12. Seeded IDs must never replace an unsaved new-device form.
  (setq catalog (EL:Get 'catalog snapshot) oldcatalog (EL:Get 'catalog (EL:Get 'snapshot *EL:DLUIState*))
    selected (EL:Get 'selected *EL:DLUIState*))
  (foreach pair (EL:Get 'drafts *EL:DLUIState*)
    (setq draft (cdr pair) identity (car pair))
    (if (= (EL:Get 'revision draft) 0)
      (cond
        ((setq base (EL:DLFindEntry (EL:Get 'block-name draft) snapshot))
          (foreach key '(block-name display watts zero-confirmed is-ground ground-confirmed active status
              watts-text aliases-text keep-old-name panel-name captured)
            (if (assoc key draft) (setq base (EL:Put key (EL:Get key draft) base))))
          (if (EL:Get 'aliases draft) (setq base (EL:Put 'aliases (EL:Get 'aliases draft) base)))
          (setq draft base))
        ((EL:By 'device-id identity (EL:Get 'devices catalog))
          (setq draft (EL:Put 'device-id (EL:DLNextID catalog) draft))))
      (if (and (setq base (EL:By 'device-id identity (EL:Get 'devices catalog)))
          (setq previous (EL:By 'device-id identity (EL:Get 'devices oldcatalog)))
          (= (EL:Get 'revision draft) (EL:Get 'revision previous))
          (equal (EL:DLUIBusinessFields previous) (EL:DLUIBusinessFields base)))
        (foreach key '(revision asset-revision block-file legend-file legend-size legend-checksum)
          (setq draft (EL:Put key (EL:Get key base) draft)))))
    (if (equal selected identity) (setq selected (EL:Get 'device-id draft)))
    (setq drafts (EL:Put (EL:Get 'device-id draft) draft drafts))
    (if (not (EL:By 'device-id (EL:Get 'device-id draft) (EL:Get 'devices catalog)))
      (setq catalog (EL:Put 'devices (append (EL:Get 'devices catalog) (list draft)) catalog))))
  (setq *EL:DLUIState* (EL:Put 'selected selected (EL:Put 'drafts drafts
    (EL:Put 'snapshot snapshot *EL:DLUIState*)))) snapshot)
(defun EL:DLUISwitchRoot (path / root snapshot outcome)
  (setq root (EL:NormalizeRoot (vl-filename-directory path)))
  ;; Validate before publishing the preference; a damaged target keeps the active library.
  (if (and (setq snapshot (EL:DLDefaultSnapshot root))
      (setq outcome (vl-catch-all-apply 'EL:DLRootSet (list root))) (not (vl-catch-all-error-p outcome)))
    (progn (setq *EL:DLUIState* (cond ((EL:Get root *EL:DLUIDirectories*))
      (T (list (cons 'snapshot snapshot) '(query . "") '(deleted) '(drafts) '(selected))))
      *EL:DLUINotice* (strcat "设备库已切换：" root)) (EL:DLUIAdoptSnapshot snapshot) T)
    (progn (EL:DLFail (strcat "设备库未切换，当前输入保留："
      (cond (*EL:DLError*) ((vl-catch-all-error-p outcome) (vl-catch-all-error-message outcome))
        (T "无法读取目标目录或保存目录设置。")))) nil)))
;; Date: 2026-10-12. Picking publishes graphics directly and retains unrelated raw edits.
(defun EL:DLUIPickEntry (name / snapshot catalog entry pair serial)
  (setq snapshot (EL:Get 'snapshot *EL:DLUIState*) catalog (EL:Get 'catalog snapshot)
    entry (EL:DLFindEntry name snapshot))
  (if (not entry)
    (progn
      (foreach pair (EL:Get 'drafts *EL:DLUIState*)
        (if (and (= (EL:Get 'revision (cdr pair)) 0)
          (or (equal (EL:DLNameKey name) (EL:DLNameKey (EL:Get 'block-name (cdr pair))))
            (equal (EL:DLNameKey name) (EL:DLNameKey (EL:Get 'panel-name (cdr pair))))))
          (setq entry (EL:Put 'device-id (car pair) (EL:DLEntryNew catalog name)))))
      (if (not entry)
        (progn (setq serial (EL:Get 'next-id catalog) entry (EL:DLEntryNew catalog name))
          (while (EL:Get (EL:Get 'device-id entry) (EL:Get 'drafts *EL:DLUIState*))
            (setq serial (1+ serial) entry (EL:DLEntryNew (EL:Put 'next-id serial catalog) name))))))) entry)
(defun EL:DLUIPublishPicked (captured / job snapshot entry candidate loaded saved draft key identity)
  (setq job (EL:Get 'captured captured) snapshot (EL:Get 'snapshot job) entry (EL:DLStrip captured)
    identity (EL:Get 'device-id entry) draft (EL:Get identity (EL:Get 'drafts *EL:DLUIState*)))
  (cond
    ((not (EL:DLSnapshotCurrent snapshot)) (EL:DLFail "设备库已变化，拾取图形保留为编辑草稿；请刷新后保存。"))
    ((and (setq entry (EL:DLAssetInstall snapshot entry (EL:Get 'dwg job) (EL:Get 'slide job)))
        (EL:DLLegend entry snapshot)
        (setq candidate (EL:DLUpsert (EL:Get 'catalog snapshot) entry)) (EL:DLCommit snapshot candidate))
      (setq loaded (EL:DLSnapshotLoad (EL:Get 'root snapshot)))
      ;; Commit has already verified the catalog. Keep that exact snapshot if a later reader is blocked.
      (if (not loaded) (setq loaded (EL:Put 'index (EL:DLIndex candidate)
        (EL:Put 'catalog candidate (EL:Put 'raw (vl-prin1-to-string candidate) (EL:Put 'present T snapshot))))))
      (setq *EL:DLUIState* (EL:Put 'selected identity (EL:Put 'query "" (EL:Put 'snapshot loaded *EL:DLUIState*)))
        *EL:DLCache* nil saved (EL:By 'device-id identity (EL:Get 'devices candidate)))
      (if draft
        (progn
          (if (EL:Get 'captured draft) (EL:DLCaptureCleanup (EL:Get 'captured draft)))
          (setq draft (vl-remove-if '(lambda (p) (equal (car p) 'captured)) draft))
          (foreach key '(revision status asset-revision block-file legend-file legend-size legend-checksum)
            (setq draft (EL:Put key (EL:Get key saved) draft)))
          (EL:DLUISetDraft draft)))
      (EL:DLCaptureCleanup job) T)
    (T nil)))
(defun EL:DLUIPickNext (/ entity entry result name suspended)
  (while (and *EL:DLUIPickQueue* (not suspended))
    (setq entity (car *EL:DLUIPickQueue*) *EL:DLUIPickQueue* (cdr *EL:DLUIPickQueue*)
      name (vl-catch-all-apply 'EL:EffectiveName (list entity)))
    (if (and (not (vl-catch-all-error-p name)) (EL:DLNameKey name))
    (progn (setq entry (EL:DLUIPickEntry name))
    (if (and (EL:DLDWGValid (strcat (EL:Get 'root (EL:Get 'snapshot *EL:DLUIState*)) (cond ((EL:Get 'block-file entry)) (T ""))))
        (EL:DLLegend entry (EL:Get 'snapshot *EL:DLUIState*)))
      (progn (setq *EL:DLUIPickReused* (1+ *EL:DLUIPickReused*))
        (setq *EL:DLUIState* (EL:Put 'query "" (EL:Put 'selected (EL:Get 'device-id entry) *EL:DLUIState*))))
      (progn
        (setq *EL:DLContinue* 'EL:DLUIPickResume
          result (vl-catch-all-apply 'EL:DLCaptureStart (list (EL:Get 'snapshot *EL:DLUIState*) entry entity)))
        (if (or (and (not (vl-catch-all-error-p result)) result) *EL:DLCaptureJob*) (setq suspended T)
          (progn (setq *EL:DLContinue* nil *EL:DLUIPickFailed* (1+ *EL:DLUIPickFailed*))
            (EL:LogEvent "DEVICE_PICK_FAILED" (list (cons 'name (EL:Get 'block-name entry))
              (cons 'message (if (vl-catch-all-error-p result) (vl-catch-all-error-message result) *EL:DLError*)))))))))
    (progn (setq *EL:DLUIPickFailed* (1+ *EL:DLUIPickFailed*))
      (EL:LogEvent "DEVICE_PICK_FAILED" (list (cons 'message "来源设备已失效，未入库；其余设备继续。"))))))
  (if suspended 'suspended
    (progn (setq *EL:DLUINotice* (strcat "拾取完成：新入库 " (itoa *EL:DLUIPickSaved*) " 种，已有 "
      (itoa *EL:DLUIPickReused*) " 种，未完成 " (itoa *EL:DLUIPickFailed*) " 种。缺功率的设备请补齐资料。")) T)))
(defun EL:DLUIPickResume (entry / result continuation)
  (setq *EL:DLContinue* nil)
  (if entry
    (progn
      (setq result (vl-catch-all-apply 'EL:DLUIPublishPicked (list entry)))
      (if (and (not (vl-catch-all-error-p result)) result)
        (setq *EL:DLUIPickSaved* (1+ *EL:DLUIPickSaved*))
        (progn
          ;; Keep the captured graphic and the user's raw fields available for retry.
          (EL:LogEvent "DEVICE_PICK_PUBLISH_FAILED" (list (cons 'name (EL:Get 'block-name entry))
            (cons 'message (if (vl-catch-all-error-p result) (vl-catch-all-error-message result) *EL:DLError*))))
          (EL:DLUISetDraft (EL:DLUICaptureEntry entry))
          (setq *EL:DLUIPickFailed* (1+ *EL:DLUIPickFailed*)))))
    (setq *EL:DLUIPickFailed* (1+ *EL:DLUIPickFailed*)))
  (if (not (equal (EL:DLUIPickNext) 'suspended))
    (progn (setq continuation (if (equal *EL:DLUIHost* 'panel) T (EL:DLUIRun)))
      (if (and (not (equal continuation 'suspended)) *EL:DLParentContinue*) (apply *EL:DLParentContinue* nil)))))
(defun EL:DLUIPickOpen ()
  (if *EL:DLCaptureJob* (c:ELDEVLIB)
    (progn (setq *EL:DLUIPickRequested* T *EL:DLParentContinue* nil) (EL:DLUIOpen))))
;; Date: 2026-10-14. Use the same library editor inside the circuit panel.
(defun EL:DLUIPanelBegin (snapshot / root key)
  (if snapshot
    (progn
      (setq root (EL:Get 'root snapshot))
      (if (or (not *EL:DLUIState*)
          (not (equal root (EL:Get 'root (EL:Get 'snapshot *EL:DLUIState*)))))
        (setq *EL:DLUIState* (list (cons 'snapshot snapshot) '(query . "") '(deleted) '(drafts)
          (cons 'selected (EL:Get 'device-id (car (EL:Get 'devices (EL:Get 'catalog snapshot)))))))
        (EL:DLUIAdoptSnapshot snapshot))
      (start_list "dl_ground") (mapcar 'add_list '("待确认" "非地面" "地面")) (end_list)
      (EL:DLUIFill)
      (EL:DLUIStatus (cond (*EL:DLError*)
        (*EL:DLCaptureJob* "图例任务尚未完成；可直接修改已有设备资料并自动保存。") (*EL:DLUINotice*)
        (T "修改后点击保存设备，核对设备名和功率；离开输入框时也会自动保存。")))
      (EL:MonitorActionTile "dl_rows" "(EL:DLUISelect $value)")
      (EL:MonitorActionTile "dl_new" "(EL:DLUINew)")
      (EL:DLUIAutoBind)
      (EL:MonitorActionTile "dl_delete" "(EL:PanelLibraryStatus T)")
      (EL:MonitorActionTile "dl_restore" "(EL:PanelLibraryStatus nil)")
      (EL:MonitorActionTile "dl_query" "(EL:DLUIQuery $value (EL:Get 'deleted *EL:DLUIState*))")
      (EL:MonitorActionTile "dl_deleted" "(EL:DLUIQuery (get_tile \"dl_query\") (equal $value \"1\"))")
      (EL:MonitorActionTile "dl_refresh" "(EL:DLUIRefresh)")
      (EL:MonitorActionTile "dl_reload" "(EL:DLUIReload)")
      (EL:MonitorActionTile "dl_directory" "(EL:DLUILeave 14)")
      (EL:MonitorActionTile "dl_pick" "(EL:DLUILeave 13)")
      (EL:MonitorActionTile "dl_export" "(EL:DLUILeave 16)")
      (EL:MonitorActionTile "dl_import" "(EL:DLUILeave 15)")
      (EL:MonitorActionTile "dl_open" "(EL:DLUILeave 20)")
      (EL:DLUIAutoSave)
      T)
    (progn
      (set_tile "dl_root" "设备库暂不可读取")
      (set_tile "dl_status" (cond (*EL:DLError*) (T "请检查设备库目录。")))
      (foreach key '("dl_rows" "dl_new" "dl_delete" "dl_restore" "dl_query"
          "dl_deleted" "dl_refresh" "dl_reload" "dl_directory" "dl_pick" "dl_export"
          "dl_import" "dl_open" "dl_block" "dl_aliases" "dl_keep_old" "dl_display" "dl_watts"
          "dl_zero" "dl_ground" "dl_active" "dl_save")
        (mode_tile key 1)) nil)))
(defun EL:DLUIRun (/ dialog status entity entry result checkpoint)
  (setq dialog (load_dialog (strcat *EL:Root* "ui/device-library.dcl"))
    status (if *EL:DLUIPickRequested* 3 2) *EL:DLUIPickRequested* nil)
  (while (and (> dialog 0) (member status '(2 3)))
    (if (= status 2) (if (new_dialog "el_device_library" dialog)
      (progn
        (start_list "dl_ground") (mapcar 'add_list '("待确认" "非地面" "地面")) (end_list)
        (EL:DLUIFill) (EL:DLUIStatus (cond (*EL:DLError*)
          (*EL:DLCaptureJob* "图例任务尚未完成；可直接修改已有设备资料并自动保存。") (*EL:DLUINotice*)
          (T "修改后点击保存设备，核对设备名和功率；离开输入框时也会自动保存。")))
        (EL:MonitorActionTile "dl_rows" "(EL:DLUISelect $value)") (EL:MonitorActionTile "dl_new" "(EL:DLUINew)")
        (EL:DLUIAutoBind)
        (EL:MonitorActionTile "dl_delete" "(EL:DLUIChangeStatus T)") (EL:MonitorActionTile "dl_restore" "(EL:DLUIChangeStatus nil)")
        (EL:MonitorActionTile "dl_query" "(EL:DLUIQuery $value (EL:Get 'deleted *EL:DLUIState*))")
        (EL:MonitorActionTile "dl_deleted" "(EL:DLUIQuery (get_tile \"dl_query\") (equal $value \"1\"))")
        (EL:MonitorActionTile "dl_refresh" "(EL:DLUIRefresh)") (EL:MonitorActionTile "dl_reload" "(EL:DLUIReload)")
        (EL:MonitorActionTile "dl_directory" "(EL:DLUILeave 4)")
        (EL:MonitorActionTile "dl_pick" "(EL:DLUILeave 3)")
        (EL:MonitorActionTile "dl_export" "(EL:DLUILeave 7)")
        (EL:MonitorActionTile "dl_import" "(EL:DLUILeave 6)")
        (EL:MonitorActionTile "dl_open" "(EL:DLUILeave 8)")
        (EL:MonitorActionTile "dl_close" "(EL:DLUILeave 0)")
        (EL:DLUIAutoSave)
        (setq status (start_dialog))) (setq status 0)))
    (cond
      ((= status 8) (setq *EL:DLUINotice* (EL:DLOpenCatalog) status 2))
      ((= status 6) (EL:DLLibraryTransferUI nil) (setq status 2))
      ((= status 7) (EL:DLLibraryTransferUI T) (setq status 2))
      ((= status 3)
        (setq checkpoint *EL:PerfPending* result (vl-catch-all-apply 'EL:DLPickDevices nil))
        (if (vl-catch-all-error-p result) (EL:PerfUnwind checkpoint))
        (if (and (not (vl-catch-all-error-p result)) result)
          (progn (setq *EL:DLUIPickQueue* result *EL:DLUIPickSaved* 0 *EL:DLUIPickReused* 0 *EL:DLUIPickFailed* 0)
            (setq status (if (equal (EL:DLUIPickNext) 'suspended) 5 2)))
          (setq *EL:DLUINotice* "本次未拾取设备；已保存资料和未保存输入保留。" status 2)))
      ((= status 4)
        (setq *EL:DLUIDirectories* (EL:Put (EL:Get 'root (EL:Get 'snapshot *EL:DLUIState*)) *EL:DLUIState* *EL:DLUIDirectories*))
        (setq result (getfiled "选择设备库的 catalog.eld" (strcat (EL:DLRoot) "catalog.eld") "eld" 0))
        (if result (EL:DLUISwitchRoot result))
        (setq status 2))))
  (if (> dialog 0) (unload_dialog dialog))
  (if (= status 5) 'suspended T))
;; Date: 2026-10-11. A blocked library has an actionable recovery window.
(defun EL:DLUILockDialog (root / dialog status recovered outcome)
  (setq dialog (load_dialog (strcat *EL:Root* "ui/device-library.dcl")) status 2)
  (while (and (> dialog 0) (= status 2))
    (if (new_dialog "el_device_library_locked" dialog)
      (progn
        (set_tile "dl_lock_root" root)
        (set_tile "dl_lock_status" (cond (*EL:DLError*) (T "请结束其他 CAD 中的设备库保存，再检查并恢复。")))
        (set_tile "dl_lock_confirm" "0") (mode_tile "dl_lock_recover" 1)
        (EL:MonitorActionTile "dl_lock_confirm" "(mode_tile \"dl_lock_recover\" (if (= $value \"1\") 0 1))")
        (EL:MonitorActionTile "dl_lock_recover" "(if (= (get_tile \"dl_lock_confirm\") \"1\") (done_dialog 3))")
        (EL:MonitorActionTile "dl_lock_retry" "(done_dialog 2)") (EL:MonitorActionTile "dl_lock_cancel" "(done_dialog 0)")
        (setq status (start_dialog))
        (cond
          ((= status 3)
            (setq outcome (vl-catch-all-apply 'EL:DLLockRecover (list root)))
            (if (and (not (vl-catch-all-error-p outcome)) outcome) (setq recovered T status 1)
              (progn (if (vl-catch-all-error-p outcome) (EL:DLFail (vl-catch-all-error-message outcome))) (setq status 2))))
          ((= status 2) (if (not (findfile (strcat root ".write-lock"))) (setq recovered T status 1)))))
      (setq status 0)))
  (if (> dialog 0) (unload_dialog dialog)) recovered)
(defun EL:DLUIOpen (/ snapshot root)
  (setq *EL:DLUIHost* 'standalone)
  (setq root (EL:DLRoot) snapshot (EL:DLDefaultSnapshot root))
  (if (and (not snapshot) (findfile (strcat root ".write-lock")))
    (if (EL:DLUILockDialog root) (setq snapshot (EL:DLDefaultSnapshot root))
      (setq root nil)))
  (if snapshot
    (progn
      (if (or (not *EL:DLUIState*) (not (equal root (EL:Get 'root (EL:Get 'snapshot *EL:DLUIState*)))))
        (setq *EL:DLUIState* (list (cons 'snapshot snapshot) '(query . "") '(deleted) '(drafts)
          (cons 'selected (EL:Get 'device-id (car (EL:Get 'devices (EL:Get 'catalog snapshot)))))))
        (EL:DLUIAdoptSnapshot snapshot))
      (EL:DLUIRun)) (progn (if root (alert (cond (*EL:DLError*) (T "无法读取设备库；原文件保留。")))) nil)))
(defun c:ELDEVLIB (/ result)
  ;; Date: 2026-10-15. Opening saved parameters never waits for legend generation.
  (setq *EL:DLParentContinue* nil *EL:DLUIPickRequested* nil
    result (vl-catch-all-apply 'EL:DLUIOpen nil))
  (if (vl-catch-all-error-p result) (princ (strcat "\n设备库窗口未完成，输入保留：" (vl-catch-all-error-message result))))
  (princ))
(princ)

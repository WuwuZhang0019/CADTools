;; Date: 2026-10-11. Read native Tianzheng circuit metadata; never write the plane.
(defun EL:NumberKey (text) (strcase (vl-string-trim " \t\r\n" text)))
(defun EL:NumberTextValid (text / code good)
  (setq good (and (equal (type text) 'STR) (/= text "")))
  (if good
    (progn
      (foreach code (vl-string->list text)
        (if (or (< code 32) (= code 127)) (setq good nil)))
      (if (vl-string-search "\\" text) (setq good nil)))) good)
(defun EL:NumberReadState (status values raw reason)
  (list (cons 'status status) (cons 'values values) (cons 'raw raw) (cons 'reason reason)))
(defun EL:ParseWireNumberDataImpl (data / row app item raw values keys text seen invalid)
  (foreach row data
    (if (and (listp row) (equal (car row) -3))
      (foreach app (cdr row)
        (if (and (listp app) (equal (type (car app)) 'STR) (equal (strcase (car app)) "LINENUM"))
          (progn
            (setq raw (cons app raw) seen nil)
            (foreach item (cdr app)
              (if (and (listp item) (equal (car item) 1000) (equal (type (cdr item)) 'STR))
                (progn
                  (setq seen T text (vl-string-trim " \t\r\n" (cdr item)))
                  (if (/= text "")
                    (if (EL:NumberTextValid text)
                      (if (not (member (EL:NumberKey text) keys))
                        (setq keys (cons (EL:NumberKey text) keys) values (cons text values)))
                      (setq invalid T))))
                (setq invalid T)))
            (if (not seen) (setq invalid T)))))))
  (EL:NumberReadState (cond (invalid 'invalid) ((> (length values) 1) 'conflict)
    (values 'ready) (T 'missing)) (reverse values) (reverse raw)
    (if invalid 'MALFORMED_LINENUM)))
(defun EL:ParseWireNumberData (data / checked)
  (setq checked (vl-catch-all-apply 'EL:ParseWireNumberDataImpl (list data)))
  (if (vl-catch-all-error-p checked)
    (EL:NumberReadState 'invalid nil nil 'MALFORMED_XDATA) checked))
(defun EL:ReadWireNumberDataImpl (handle / entity checked state)
  (setq checked (vl-catch-all-apply 'handent (list handle)))
  (if (or (vl-catch-all-error-p checked) (not checked))
    (setq state (EL:NumberReadState 'invalid nil nil 'MISSING_SOURCE_WIRE))
    (progn
      (setq entity checked checked (vl-catch-all-apply 'entget (list entity '("linenum"))))
      (cond ((vl-catch-all-error-p checked)
          (setq state (EL:NumberReadState 'invalid nil nil 'READ_FAILED)))
        ((not checked) (setq state (EL:NumberReadState 'invalid nil nil 'MISSING_SOURCE_WIRE)))
        ((not (member (cdr (assoc 0 checked)) '("LINE" "LWPOLYLINE")))
          (setq state (EL:NumberReadState 'invalid nil nil 'NOT_A_SOURCE_WIRE)))
        ((not (equal (strcase (cond ((cdr (assoc 5 checked))) (T ""))) (strcase handle)))
          (setq state (EL:NumberReadState 'invalid nil nil 'SOURCE_HANDLE_MISMATCH)))
        (T (setq state (EL:ParseWireNumberData checked))))))
  state)
(defun EL:ReadWireNumberData (handle / checked)
  (EL:PerfCount "number-source-read-attempts" 1)
  (setq checked (vl-catch-all-apply 'EL:ReadWireNumberDataImpl (list handle)))
  (setq checked (EL:Put 'handle handle (if (vl-catch-all-error-p checked)
    (EL:NumberReadState 'invalid nil nil 'MALFORMED_SOURCE_DATA) checked)))
  (if (equal (EL:Get 'status checked) 'invalid) (EL:PerfCount "number-source-read-failures" 1))
  (EL:LogEvent "CIRCUIT_NUMBER_READ" (list (cons 'handle handle) (cons 'status (EL:Get 'status checked))
    (cons 'values (EL:Get 'values checked)) (cons 'reason (EL:Get 'reason checked)))) checked)
;; Ordered path stations use the same sampled geometry and width profiles as recognition.
(defun EL:NumberPathLength (wire / total segment)
  (setq total 0.0)
  (foreach segment (EL:Get 'segments wire)
    (setq total (+ total (EL:Norm (EL:V- (cadr segment) (car segment)))))) total)
(defun EL:NumberPathMeasures (wire / cursor segment vector length rows)
  ;; Date: 2026-10-15. Exact segment lengths/vectors are constant across the
  ;; 32 prefix probes; retain the original arithmetic and accumulation order.
  (setq cursor 0.0)
  (foreach segment (EL:Get 'segments wire)
    (setq vector (EL:V- (cadr segment) (car segment)) length (EL:Norm vector)
      rows (cons (list (car segment) vector cursor length) rows) cursor (+ cursor length)))
  (reverse rows))
(defun EL:NumberPathSlice (wire start finish)
  (EL:NumberPathSliceMeasured wire start finish (EL:NumberPathMeasures wire)))
(defun EL:NumberPathSliceMeasured (wire start finish measures / low high row point vector cursor length a b part segments)
  (setq low (min start finish) high (max start finish))
  (foreach row measures
    (setq point (car row) vector (cadr row) cursor (caddr row) length (nth 3 row)
      a (max low cursor) b (min high (+ cursor length)))
    (if (and (> length 1.0e-12) (> b a))
      (progn
        (setq part (list
          (EL:V+ point (EL:V* (/ (- a cursor) length) vector))
          (EL:V+ point (EL:V* (/ (- b cursor) length) vector))))
        (setq segments (cons part segments)))))
  (setq segments (reverse segments))
  (if (> start finish) (setq segments (mapcar '(lambda (s) (reverse s)) (reverse segments))))
  (EL:Put 'contact-strips (EL:WireContactStrips segments (EL:Get 'width-profiles wire))
    (EL:Put 'segments segments wire)))
(defun EL:NumberStations (point wire cfg / cursor segment vector length fraction nearest station out)
  (setq cursor 0.0)
  (foreach segment (EL:Get 'segments wire)
    (setq vector (EL:V- (cadr segment) (car segment)) length (EL:Norm vector))
    (if (> length 1.0e-12)
      (progn
        (setq fraction (max 0.0 (min 1.0 (/ (EL:Dot (EL:V- point (car segment)) vector) (* length length))))
          nearest (EL:V+ (car segment) (EL:V* fraction vector)) station (+ cursor (* fraction length)))
        (if (and (EL:Touches point (list segment) (EL:Get 'eps_touch (EL:Get 'params cfg)) (EL:GapEpsilon))
            (not (vl-some '(lambda (old) (equal old station (EL:GapEpsilon))) out)))
          (setq out (cons station out)))))
    (setq cursor (+ cursor length))) (reverse out))
(defun EL:NumberRootStation (wire snapshot cfg panel / segments first last a b root)
  (setq segments (EL:Get 'segments wire) first (caar segments) last (cadr (EL:Last segments)))
  (if (setq root (EL:By 'wire (EL:Get 'id wire) (EL:Get 'circuit-starts snapshot)))
    (list (if (equal (EL:Get 'end root) 'start) 0.0 (EL:NumberPathLength wire)))
  (if (and first last)
    (progn
      (setq a (if (EL:Get 'trunk-segments snapshot) (EL:TrunkPoint first (EL:Get 'trunk-segments snapshot))
        (EL:BlockPointHit first panel cfg))
        b (if (EL:Get 'trunk-segments snapshot) (EL:TrunkPoint last (EL:Get 'trunk-segments snapshot))
          (EL:BlockPointHit last panel cfg)))
      (cond ((and a (not b)) (list 0.0)) ((and b (not a)) (list (EL:NumberPathLength wire))))))))
(defun EL:NumberShapeHit (wire shape cfg)
  (EL:NumberShapeHitStrict wire shape (EL:StrictDeviceConfig cfg)))
(defun EL:NumberShapeHitStrict (wire shape cfg)
  (or (if *EL:NumberProbeActive* (EL:NumberProbePathHit wire shape cfg) (EL:ContourPathHit wire shape cfg))
    (EL:WideDevicePathHit wire shape cfg)))
(defun EL:NumberProbePointHit (point shape cfg / key saved hit)
  ;; Date: 2026-10-15. Exact point/shape keys; the strict config is fixed for
  ;; this one binary search. NIL is a cached miss, not an absent entry.
  (setq key (cons point shape))
  (if (setq saved (assoc key *EL:NumberProbePoints*)) (cdr saved)
    (progn (setq hit (EL:BlockPointHit point shape cfg)
      *EL:NumberProbePoints* (cons (cons key hit) *EL:NumberProbePoints*)) hit)))
(defun EL:NumberProbePathHit (wire shape cfg / hit seg edge segments candidates key saved tol)
  ;; Same ordered predicates as ContourPathHit. Only identical points and
  ;; completed segments are memoized; the 32-step grid is unchanged.
  (setq segments (EL:Get 'segments wire) tol (EL:Get 'eps_boundary (EL:Get 'params cfg)))
  (while (and segments (not hit))
    (setq seg (car segments) segments (cdr segments) key (cons seg shape))
    (if (setq saved (assoc key *EL:NumberProbeSegments*)) (setq hit (cdr saved))
      (progn
        (if (or (EL:NumberProbePointHit (car seg) shape cfg) (EL:NumberProbePointHit (cadr seg) shape cfg)
            (EL:RegionContains (EL:V* 0.5 (EL:V+ (car seg) (cadr seg))) shape)) (setq hit T))
        (if (not hit) (setq hit (vl-some '(lambda (curve) (EL:CurveSegmentHit seg curve tol)) (EL:Get 'curves shape))))
        (if (not hit) (setq candidates (EL:ContactSegmentsTolerance shape (EL:SegmentBounds (list seg)) tol)))
        (while (and candidates (not hit))
          (setq edge (car candidates) candidates (cdr candidates))
          (if (EL:SegmentsTouchTolerance seg edge tol) (setq hit T)))
        (setq *EL:NumberProbeSegments* (cons (cons key hit) *EL:NumberProbeSegments*))))) hit)
(defun EL:NumberFirstDevice (wire entry target devices cfg / block shape candidates hits row low high middle slice measures
    *EL:NumberProbeActive* *EL:NumberProbePoints* *EL:NumberProbeSegments*)
  ;; Date: 2026-10-15. All devices share the same 32-step dyadic prefix grid.
  ;; Search the first contact jointly; on a hit retain every device hitting
  ;; that prefix, in original order. This preserves the exact boundary and
  ;; original first-device tie rule without rebuilding each prefix per device.
  (if (and devices (> (abs (- target entry)) 1.0e-12))
    (progn
    (setq *EL:NumberProbeActive* T cfg (EL:StrictDeviceConfig cfg) measures (EL:NumberPathMeasures wire)
      slice (EL:NumberPathSliceMeasured wire entry target measures))
    (foreach block devices
      (setq shape (EL:DeviceContactShape block))
      (if (EL:NumberShapeHitStrict slice shape cfg)
        (setq candidates (cons (cons (EL:Get 'id block) shape) candidates))))
    (if candidates
      (progn
        (setq candidates (reverse candidates) low 0.0 high 1.0)
        (repeat 32
          (setq middle (/ (+ low high) 2.0) hits nil
            slice (EL:NumberPathSliceMeasured wire entry (+ entry (* middle (- target entry))) measures))
          (foreach row candidates
            (if (EL:NumberShapeHitStrict slice (cdr row) cfg) (setq hits (cons row hits))))
          (if hits (setq high middle candidates (reverse hits)) (setq low middle)))
        (list (+ entry (* high (- target entry))) (caar candidates)))))))
(defun EL:NumberLinks (wire other network cfg / segments point stations mine theirs links pair a b)
  (setq segments (EL:Get 'segments wire))
  (foreach point (list (caar segments) (cadr (EL:Last segments)))
    (setq mine (EL:NumberStations point wire cfg) theirs (EL:NumberStations point other cfg))
    (if (and (= (length mine) 1) (= (length theirs) 1))
      (setq links (cons (list (car mine) (car theirs)) links))))
  (setq segments (EL:Get 'segments other))
  (foreach point (list (caar segments) (cadr (EL:Last segments)))
    (setq mine (EL:NumberStations point wire cfg) theirs (EL:NumberStations point other cfg))
    (if (and (= (length mine) 1) (= (length theirs) 1))
      (setq links (cons (list (car mine) (car theirs)) links))))
  (foreach pair (EL:Get 'gap-pairs network)
    (setq a (EL:Get 'a pair) b (EL:Get 'b pair))
    (if (and (equal (car b) (EL:Get 'id wire)) (equal (car a) (EL:Get 'id other)))
      (setq a (EL:Get 'b pair) b (EL:Get 'a pair)))
    (if (and (equal (car a) (EL:Get 'id wire)) (equal (car b) (EL:Get 'id other)))
      (setq links (cons (list (if (equal (cadr a) 'start) 0.0 (EL:NumberPathLength wire))
        (if (equal (cadr b) 'start) 0.0 (EL:NumberPathLength other))) links))))
  (EL:Unique links))
(defun EL:ExitNumberScopeImpl (seed network cfg / snapshot panel wires edges root start queue visited step id entry wire devices
    next other left right low high link links sources boundaries ranges issues source)
  (setq snapshot (EL:Get 'snapshot network) panel (EL:By 'id (EL:Get 'panel network) (EL:Get 'blocks snapshot))
    wires (EL:Get 'wires snapshot) edges (EL:Get 'edges network)
    root (EL:By 'id (EL:Get 'wire seed) wires) start (EL:NumberRootStation root snapshot cfg panel))
  (if (not start) (setq issues (list (EL:Issue 'NUMBER_EXIT_DIRECTION (EL:Get 'wire seed) nil)))
    (setq queue (list (list (EL:Get 'wire seed) (car start)))))
  (while queue
    (setq step (car queue) queue (cdr queue) id (car step) entry (cadr step))
    (if (not (vl-some '(lambda (old) (and (equal id (car old)) (equal entry (cadr old) (EL:GapEpsilon)))) visited))
      (progn
        (setq visited (cons step visited) wire (EL:By 'id id wires)
          source (cond ((EL:Get 'source-wire wire)) (T id)) sources (cons source sources)
          devices nil)
        (foreach next (EL:Neighbours id edges)
          (if (and (not (equal next (EL:Get 'panel network)))
              (setq other (EL:By 'id next (EL:Get 'blocks snapshot)))) (setq devices (cons other devices))))
        (setq left (EL:NumberFirstDevice wire entry 0.0 devices cfg)
          right (EL:NumberFirstDevice wire entry (EL:NumberPathLength wire) devices cfg)
          low (if left (car left) 0.0) high (if right (car right) (EL:NumberPathLength wire)))
        (if left (setq boundaries (cons (cadr left) boundaries)))
        (if right (setq boundaries (cons (cadr right) boundaries)))
        (setq ranges (cons (list id entry low high) ranges))
        (foreach next (EL:Neighbours id edges)
          (if (setq other (EL:By 'id next wires))
            (progn
              (setq links (EL:NumberLinks wire other network cfg))
              (if (not links) (setq issues (cons (EL:Issue 'NUMBER_CONNECTION_POSITION id next) issues)))
              (foreach link links
                (if (and (if left (> (car link) (+ low (EL:GapEpsilon))) (>= (car link) low))
                    (if right (< (car link) (- high (EL:GapEpsilon))) (<= (car link) high)))
                  (setq queue (append queue (list (list next (cadr link)))))))))))))
  (list (cons 'status (if issues 'path-ambiguous 'ready)) (cons 'sources (EL:Unique (reverse sources)))
    (cons 'boundaries (EL:Unique (reverse boundaries))) (cons 'ranges (reverse ranges)) (cons 'issues issues)))
(defun EL:ExitNumberScope (seed network cfg / checked)
  (EL:PerfCount "number-scopes" 1)
  (setq checked (vl-catch-all-apply 'EL:ExitNumberScopeImpl (list seed network cfg)))
  (setq checked (if (vl-catch-all-error-p checked)
    (list '(status . invalid) (cons 'issues (list (EL:Issue 'NUMBER_SCOPE_FAILED (EL:Get 'wire seed)
      (vl-catch-all-error-message checked))))) checked))
  (EL:LogEvent "CIRCUIT_NUMBER_SCOPE" (list (cons 'panel (EL:Get 'panel network)) (cons 'seed (EL:Get 'key seed))
    (cons 'wire (EL:Get 'wire seed)) (cons 'status (EL:Get 'status checked))
    (cons 'sources (EL:Get 'sources checked)) (cons 'boundaries (EL:Get 'boundaries checked))
    (cons 'issues (mapcar '(lambda (issue) (EL:Get 'code issue)) (EL:Get 'issues checked))))) checked)
;; Resolve only after stable identities and the final display order have been restored.
(defun EL:NumberSourceInputs (circuits / c handle inputs)
  (foreach c circuits
    (foreach handle (EL:Get 'sources (EL:Get 'number-scope c))
      (if (not (EL:By 'handle handle inputs))
        (setq inputs (cons (EL:ReadWireNumberData handle) inputs)))))
  (EL:PerfSet "number-source-handles" (length inputs)) (reverse inputs))
;; Date: 2026-10-13. A common unnumbered feeder can supply independently numbered arms.
;; Remove numbered wires from the pre-device graph. An unnumbered component belongs
;; to one arm only when it touches exactly one native number; shared parts are boundary.
(defun EL:NumberBranchCircuits (c network cfg inputs / scope snapshot wires sources ids marked labels key row wire id
    edges plain components visited component neighbours names root shared good branches allowed blocked seed branch group devices)
  (setq scope (EL:Get 'number-scope c) snapshot (EL:Get 'snapshot network)
    wires (EL:Get 'wires snapshot) sources (EL:Get 'sources scope) good (equal (EL:Get 'status scope) 'ready))
  (foreach wire wires
    (setq id (EL:Get 'id wire) row (EL:By 'handle (cond ((EL:Get 'source-wire wire)) (T id)) inputs))
    (if (member (EL:Get 'handle row) sources)
      (progn
        (setq ids (cons id ids))
        (cond ((equal (EL:Get 'status row) 'ready)
            (setq key (EL:NumberKey (car (EL:Get 'values row))) marked (EL:Put id key marked)
              labels (EL:Put key (cons id (EL:Get key labels)) labels)))
          ((not (equal (EL:Get 'status row) 'missing)) (setq good nil))))))
  (setq root (EL:Get 'wire (EL:Get 'seed c)))
  (if (and good (> (length labels) 1) (member root ids) (not (EL:Get root marked))
      (not (EL:Get 'trunk-segments snapshot)))
    (progn
      (setq edges (vl-remove-if-not '(lambda (e) (and (member (car e) ids) (member (cadr e) ids)))
        (EL:Get 'edges network))
        plain (vl-remove-if '(lambda (e) (or (EL:Get (car e) marked) (EL:Get (cadr e) marked))) edges))
      (foreach id ids
        (if (and (not (EL:Get id marked)) (not (member id visited)))
          (progn
            (setq component (EL:Component id plain) visited (append component visited) names nil)
            (foreach wire component
              (foreach key (EL:Neighbours wire edges)
                (if (setq group (EL:Get key marked)) (setq names (cons group names)))))
            (setq names (EL:Unique names) components (cons (list component names) components))
            (if (member root component) (setq shared names)))))
      ;; Every native number must be a parallel arm directly off the same feeder.
      ;; Serial conflicting labels never satisfy this condition.
      (if (= (length shared) (length labels))
        (foreach group labels
          (setq allowed (cdr group))
          (foreach component components
            (if (equal (cadr component) (list (car group)))
              (setq allowed (append allowed (car component)))))
          (setq blocked (vl-remove-if '(lambda (wire) (member wire allowed)) ids)
            id (car (vl-sort (cdr group) '<))
            wire (EL:By 'id id wires)
            seed (list (cons 'id (EL:Get 'id c)) (cons 'wire id)
              (cons 'key (list (cond ((EL:Get 'source-wire wire)) (T id)) 'outlet)))
            branch (EL:TraceCircuit seed (EL:CircuitSnapshot snapshot (EL:Get 'panel network))
              (vl-remove-if '(lambda (e) (or (member (EL:Get 'panel network) e)
                (member (car e) blocked) (member (cadr e) blocked))) (EL:Get 'edges network))
              (EL:Get 'gap-issues network)))
          (setq branch (EL:Put 'number-scope (list '(status . ready)
            (cons 'sources (EL:Unique (mapcar '(lambda (wire)
              (cond ((EL:Get 'source-wire (EL:By 'id wire wires))) (T wire))) allowed)))
            (cons 'shared-feeder (EL:Get 'sources scope))) branch)
            branches (cons branch branches)))
        (setq branches nil))))
  ;; A missing/unmarked arm must not disappear just to resolve the number error.
  (foreach branch branches (setq devices (append devices (EL:Get 'devices branch))))
  (if (vl-some '(lambda (id) (not (member id devices))) (EL:Get 'devices c)) (setq branches nil))
  (if branches (EL:LogEvent "CIRCUIT_NUMBER_BRANCH_SPLIT" (list (cons 'seed (EL:Get 'key (EL:Get 'seed c)))
    (cons 'numbers (mapcar 'car labels)) (cons 'branch-count (length branches)))))
  (reverse branches))
(defun EL:SplitNativeNumberBranches (result network cfg / inputs out c branches index candidate)
  (setq inputs (EL:NumberSourceInputs (EL:Get 'circuits result)))
  (foreach c (EL:Get 'circuits result)
    (setq candidate (EL:NumberCandidate c inputs)
      branches (if (and (equal (EL:Get 'status (EL:Get 'number-scope c)) 'ready)
        (> (length (EL:Get 'candidates (EL:Get 'number-evidence candidate))) 1))
        (EL:NumberBranchCircuits c network cfg inputs)))
    (foreach c (cond (branches) (T (list c))) (setq out (cons c out))))
  (setq out (reverse out) index 0)
  (setq out (mapcar '(lambda (c) (setq index (1+ index)) (EL:Put 'id (strcat "R" (itoa index)) c)) out))
  (EL:Put 'number-policy-version 1 (EL:Put 'number-inputs inputs (EL:Put 'circuits out
    (EL:Put 'complete (and out (not (EL:Get 'issues (EL:Get 'snapshot result)))
      (vl-every '(lambda (c) (EL:Get 'complete c)) out)) result)))))
(defun EL:NumberCandidate (c inputs / scope handle row values keys text status evidence source)
  (setq scope (EL:Get 'number-scope c) status (cond ((EL:Get 'status scope)) (T 'ready)))
  (foreach handle (EL:Get 'sources scope)
    (setq row (EL:By 'handle handle inputs) evidence (cons row evidence))
    (if (equal (EL:Get 'status row) 'invalid) (setq status 'invalid))
    (if (and (equal (EL:Get 'status row) 'conflict) (not (equal status 'invalid))) (setq status 'conflict))
    (foreach text (EL:Get 'values row)
      (if (not (member (EL:NumberKey text) keys))
        (setq keys (cons (EL:NumberKey text) keys) values (cons text values)))))
  (setq values (reverse values))
  (if (and (> (length values) 1) (equal status 'ready)) (setq status 'conflict))
  (if (and (not scope) (EL:NumberTextValid (EL:Get 'circuit-number c)))
    (setq values (list (EL:Get 'circuit-number c))))
  (setq source (if scope (if values 'plane 'auto) 'legacy))
  (EL:Put 'number-evidence (list (cons 'scope scope) (cons 'inputs (reverse evidence)) (cons 'candidates values))
    (EL:Put 'number-status status (EL:Put 'number-source source
      (EL:Put 'circuit-number (if (= (length values) 1) (car values)) c)))))
(defun EL:DefaultCircuitNumber (index used / text)
  (setq text (strcat "ZE" (itoa index)))
  (while (member (EL:NumberKey text) used)
    (setq index (1+ index) text (strcat "ZE" (itoa index)))) text)
;; Date: 2026-10-13. Sort ZE slots numerically after resolving their native numbers.
(defun EL:ZENumberIndex (c / text index code good)
  (setq text (EL:Get 'circuit-number c))
  (if (and (equal (EL:Get 'number-status c) 'ready) (EL:NumberTextValid text)
      (> (strlen text) 2) (equal (substr (strcase text) 1 2) "ZE"))
    (progn
      (setq index 3 good T)
      (while (and good (<= index (strlen text)))
        (setq code (ascii (substr text index 1)) good (and (>= code 48) (<= code 57))
          index (1+ index)))
      (if good (atoi (substr text 3))))))
(defun EL:SortCircuitNumbers (result / circuits c key index numbered out)
  (setq circuits (EL:Get 'circuits result) index 0)
  (foreach c circuits
    (if (setq key (EL:ZENumberIndex c))
      (setq numbered (cons (list key index c) numbered)))
    (setq index (1+ index)))
  ;; The original index breaks ties so vl-sort cannot discard equal-number rows.
  (setq numbered (vl-sort numbered '(lambda (a b)
    (if (= (car a) (car b)) (< (cadr a) (cadr b)) (< (car a) (car b))))))
  (foreach c circuits
    (if (EL:ZENumberIndex c)
      (setq c (caddr (car numbered)) numbered (cdr numbered)))
    (setq out (cons c out)))
  ;; Keep UID, saved allocation order, power and all per-circuit settings attached.
  ;; Custom numbers and unresolved rows retain their original slots.
  (EL:Put 'circuits (reverse out) result))
(defun EL:ResolveCircuitNumbers (result / inputs rows c text used counts sources owners handle key conflicts out index problems)
  ;; Repreparing a displayed draft must keep its original metadata baseline.
  ;; Only a newly recognized result reads inputs; FreshResult checks later changes.
  (setq inputs (if (assoc 'number-policy-version result) (EL:Get 'number-inputs result)
    (EL:NumberSourceInputs (EL:Get 'circuits result))))
  (foreach c (EL:Get 'circuits result)
    (setq c (EL:NumberCandidate c inputs) rows (cons c rows)
      key (EL:Get 'circuit-uid c))
    (foreach handle (EL:Get 'sources (EL:Get 'number-scope c))
      (setq owners (EL:Get handle sources))
      (if (not (member key owners)) (setq sources (EL:Put handle (cons key owners) sources))))
    (foreach text (EL:Get 'candidates (EL:Get 'number-evidence c))
      (setq key (EL:NumberKey text) used (cons key used)
        counts (EL:Put key (1+ (cond ((EL:Get key counts)) (T 0))) counts))))
  (setq rows (reverse rows) index 0)
  (foreach c rows
    (setq index (1+ index) text (EL:Get 'circuit-number c) conflicts nil)
    (foreach handle (EL:Get 'sources (EL:Get 'number-scope c))
      (if (> (length (EL:Get handle sources)) 1) (setq conflicts (cons handle conflicts))))
    (cond (conflicts
        (setq c (EL:Put 'number-status 'path-ambiguous (EL:Put 'number-evidence
          (EL:Put 'shared-sources conflicts (EL:Get 'number-evidence c)) c))))
      ((and text (> (EL:Get (EL:NumberKey text) counts) 1))
        (setq c (EL:Put 'number-status 'conflict c))))
    (if (and (not text) (equal (EL:Get 'number-status c) 'ready))
      (progn (setq text (EL:DefaultCircuitNumber index used) used (cons (EL:NumberKey text) used)
        c (EL:Put 'circuit-number text c))))
    (if (not (equal (EL:Get 'number-status c) 'ready)) (setq problems (1+ (cond (problems) (T 0)))))
    (EL:LogEvent (if (equal (EL:Get 'number-status c) 'ready) "CIRCUIT_NUMBER_RESOLVED" "CIRCUIT_NUMBER_CONFLICT")
      (list (cons 'panel (EL:Get 'panel result)) (cons 'circuit-uid (EL:Get 'circuit-uid c))
        (cons 'seed-key (EL:Get 'seed-key c)) (cons 'index index) (cons 'number text)
        (cons 'source (EL:Get 'number-source c)) (cons 'status (EL:Get 'number-status c))
        (cons 'sources (EL:Get 'sources (EL:Get 'number-scope c)))
        (cons 'candidates (EL:Get 'candidates (EL:Get 'number-evidence c)))
        (cons 'reason (cond ((not (equal (EL:Get 'number-status c) 'ready)) 'review-required)
          ((equal (EL:Get 'number-source c) 'plane) 'linenum)
          ((equal (EL:Get 'number-source c) 'legacy) 'legacy-compatible)
          ((equal text (strcat "ZE" (itoa index))) 'default-order) (T 'default-avoid-occupied)))))
    (setq out (cons c out)))
  (EL:PerfSet "number-problems" (cond (problems) (T 0)))
  (EL:Put 'number-policy-version 1 (EL:Put 'number-inputs inputs (EL:Put 'circuits (reverse out) result))))
(defun EL:CircuitNumberText (c index)
  (cond ((EL:NumberTextValid (EL:Get 'circuit-number c)) (EL:Get 'circuit-number c))
    ((and (assoc 'number-status c) (not (equal (EL:Get 'number-status c) 'ready))) "编号待核对")
    (T (strcat "ZE" (itoa index)))))
(defun EL:CircuitNumbersReady (result)
  (vl-every '(lambda (c) (or (not (assoc 'number-status c)) (equal (EL:Get 'number-status c) 'ready)))
    (EL:Get 'circuits result)))
(defun EL:NumberProblemText (result / c problem text value values handles handle)
  (foreach c (EL:Get 'circuits result)
    (if (and (assoc 'number-status c) (not (equal (EL:Get 'number-status c) 'ready)) (not problem))
      (setq problem c)))
  (if problem
    (progn
      (setq text (cond ((equal (EL:Get 'number-status problem) 'conflict) "回路编号冲突")
        ((equal (EL:Get 'number-status problem) 'path-ambiguous) "编号首段或归属待核对")
        (T "回路编号读取异常")))
      (foreach value (EL:Get 'candidates (EL:Get 'number-evidence problem))
        (setq values (strcat (cond (values) (T "")) (if values "、" "") value)))
      (foreach handle (EL:Get 'sources (EL:Get 'number-scope problem))
        (setq handles (strcat (cond (handles) (T "")) (if handles "、" "") handle)))
      (strcat text (if values (strcat "：" values) "") (if handles (strcat "；导线 " handles) "")
        "。请在平面核对后重新统计；当前可编辑功率和保存草稿。"))))
(defun EL:NumberFormalFields (c row)
  (list (cons 'circuit-number (EL:Get 'circuit-number row))
    (cons 'number-source (cond ((EL:Get 'number-source c)) ((equal (EL:Get 'mode row) 'reserve) 'auto) (T 'legacy)))
    (cons 'number-status (cond ((EL:Get 'number-status c)) (T 'ready)))
    (cons 'number-evidence (EL:Get 'number-evidence c)) (cons 'number-scope (EL:Get 'number-scope c))))
(defun EL:RecordNumberInputs (record result draft / key target)
  (if (assoc 'number-policy-version result)
    (foreach key '(number-policy-version number-inputs)
      (setq target (if draft (if (equal key 'number-inputs) 'draft-number-inputs 'draft-number-policy-version) key)
        record (EL:Put target (EL:Get key result) record))))
  (if (not draft) (setq record (EL:Put 'draft-number-inputs nil (EL:Put 'draft-number-policy-version nil record)))) record)
(defun EL:NumberInputsCurrent (result / expected actual good)
  (EL:PerfCount "number-freshness-checks" 1)
  (setq good T)
  (foreach expected (EL:Get 'number-inputs result)
    (setq actual (EL:ReadWireNumberData (EL:Get 'handle expected)))
    (if (not (equal expected actual))
      (progn (setq good nil)
        (EL:LogEvent "SOURCE_NUMBER_CHANGED" (list (cons 'handle (EL:Get 'handle expected))
          (cons 'before-status (EL:Get 'status expected)) (cons 'after-status (EL:Get 'status actual))
          (cons 'before (EL:Get 'values expected)) (cons 'after (EL:Get 'values actual))))))) good)
(princ)

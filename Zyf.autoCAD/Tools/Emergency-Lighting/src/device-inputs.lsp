;; Date: 2026-10-11. Drawing-local manual inputs; UTF-8 and independent of package versions.
(defun EL:DLOverridesValid (rows / good pair value key seen)
  (setq good (listp rows))
  (foreach pair rows
    (setq key (car pair) value (cdr pair))
    (if (or (not (EL:DLNameKey key)) (member key seen)
        (not (EL:OnlyKeys value '(watts watts-set is-ground ground-set)))
        (and (EL:Get 'watts-set value) (or (not (assoc 'watts value))
          (and (EL:Get 'watts value) (not (EL:DLInt (EL:Get 'watts value))))))
        (and (assoc 'watts-set value) (not (EL:DLBoolField 'watts-set value)))
        (and (assoc 'ground-set value) (not (EL:DLBoolField 'ground-set value)))
        (and (EL:Get 'ground-set value) (not (EL:DLBoolField 'is-ground value)))) (setq good nil))
    (setq seen (cons key seen))) good)
(defun EL:DLInputsValid (data)
  (and (EL:OnlyKeys data '(schema powers device-overrides)) (equal (EL:Get 'schema data) 'EL_DEVICE_INPUTS_V1)
    (EL:SimplePowersValid (list '(version . 1) (cons 'powers (EL:Get 'powers data))))
    (EL:DLOverridesValid (EL:Get 'device-overrides data))))
(defun EL:DLInputsPath (panel / base drawing)
  (if (and panel (setq base (getenv "LOCALAPPDATA")) (setq drawing (EL:DrawingID)))
    (strcat (EL:NormalizeRoot base) "Emergency-Lighting/drawing-inputs/"
      (EL:Hash (strcat drawing "/" (getvar "DWGPREFIX") (getvar "DWGNAME") "/" panel)) ".eld")))
(defun EL:DLInputsRead (panel / path data)
  (if (and (setq path (EL:DLInputsPath panel)) (findfile path))
    (progn (setq data (EL:StoreParse (EL:DLReadText path)))
      (if (EL:DLInputsValid data) data (EL:DLFail "本箱手填缓存损坏，原文件保留；已保存 DWG 的值仍可用。")))))
(defun EL:DLLoadInputs (panel / data)
  (setq data (vl-catch-all-apply 'EL:DLInputsRead (list panel)))
  (if (vl-catch-all-error-p data) nil data))
(defun EL:DLInputsPublish (path data / folder temporary backup current result)
  (setq folder (vl-filename-directory path))
  (EL:Require (and (EL:DLInputsValid data) (EL:DLMkdir folder)) "本箱手填缓存目录不可写。")
  (if (findfile path)
    (EL:Require (EL:DLInputsValid (EL:StoreParse (EL:DLReadText path))) "原手填缓存损坏，未覆盖；请先保留并检查原文件。"))
  (setq temporary (vl-filename-mktemp "inputs-" folder ".eld") backup (vl-filename-mktemp "previous-" folder ".eld"))
  (EL:Require (and (EL:DLWriteText temporary (vl-prin1-to-string data))
    (equal (EL:StoreParse (EL:DLReadText temporary)) data)) "本箱手填缓存回读失败，原文件保留。")
  (if (findfile path) (EL:Require (vl-file-rename path backup) "原手填缓存无法保留，未替换。"))
  (setq result (vl-catch-all-apply 'vl-file-rename (list temporary path)))
  (if (or (vl-catch-all-error-p result) (not result))
    (progn (if (findfile backup) (vl-file-rename backup path)) (EL:Require nil "本箱手填缓存发布失败，已尝试恢复原文件。")))
  (setq result (vl-catch-all-apply 'EL:StoreParse (list (EL:DLReadText path))))
  (if (not (equal result data))
    (progn (vl-file-delete path) (if (findfile backup) (vl-file-rename backup path))
      (EL:Require nil "本箱手填缓存发布回读失败，已尝试恢复原文件。")))
  (if (findfile backup) (vl-file-delete backup)) T)
(defun EL:DLRememberInputs (result powers / path data lock owner written)
  (setq path (EL:DLInputsPath (EL:Get 'panel result)) owner (EL:DLOperationID)
    data (list '(schema . EL_DEVICE_INPUTS_V1) (cons 'powers (vl-remove-if-not '(lambda (p) (numberp (cdr p))) powers))
      (cons 'device-overrides (EL:Get 'device-overrides result))))
  (if (and path (EL:DLMkdir (vl-filename-directory path)))
    (progn (setq lock (strcat path ".lock"))
      (if (EL:DLLockAcquire lock owner)
        (progn (setq written (vl-catch-all-apply 'EL:DLInputsPublish (list path data))) (EL:DLLockRelease lock owner)
          (if (vl-catch-all-error-p written) (EL:DLFail (vl-catch-all-error-message written)) written))))))
;; Date: 2026-10-13. Publish edited powers in one catalog transaction, retaining all other fields.
(princ)

(defun EL:DrawingID ()
  (if (= (getvar "DWGTITLED") 1)
    (strcase (strcat (getvar "DWGPREFIX") (getvar "DWGNAME")))))
(defun EL:NormalizeRoot (root)
  (if (and (equal (type root) 'STR) (/= root ""))
    (strcat (vl-string-right-trim "/\\" root) "/")))
(defun EL:RootValid (root / ok file folder)
  (if (setq root (EL:NormalizeRoot root))
    (progn
      (setq ok T)
      (foreach file '("src/load.lsp" "src/common.lsp" "src/config.lsp" "src/geometry.lsp"
                     "src/topology.lsp" "src/statistics.lsp" "src/generation.lsp"
                     "src/main.lsp" "src/simple.lsp" "src/circuit-number.lsp" "src/fixed.lsp" "src/panel.lsp"
                     "src/store-compact.lsp" "src/diagram-store.lsp" "src/store-split.lsp" "src/diagram-update.lsp" "src/diagram-commands.lsp" "src/insert-circuit.lsp" "src/device-library.lsp" "src/device-assets.lsp" "src/device-defaults.lsp" "src/device-ui.lsp" "src/device-recognition.lsp" "src/device-inputs.lsp" "src/device-migration.lsp" "ui/device-library.dcl" "ui/power.dcl")
        (if (not (findfile (strcat root file))) (setq ok nil)))
      (foreach folder '("templates")
        (if (not (vl-file-directory-p (strcat root folder))) (setq ok nil)))
      (and ok (findfile (strcat root *EL:LiteMarker*)) (EL:BoxUIValid root)))))
(defun EL:BoxUIValid (root)
  (and (findfile (strcat root "ui/box-ui-011.marker")) (findfile (strcat root "ui/diagram-ui-044.marker"))))
(defun EL:RootFromLoad (path / name extension directory root)
  (if (and (equal (type path) 'STR) (/= path "")
           (setq name (vl-filename-base path)) (equal (type name) 'STR)
           (equal (strcase name) "LOAD")
           (setq extension (vl-filename-extension path)) (equal (type extension) 'STR)
           (equal (strcase extension) ".LSP")
           (setq directory (vl-filename-directory path)) (/= directory ""))
    (progn
      (setq root (EL:NormalizeRoot (strcat directory "/../")))
      (if (EL:RootValid root) root))))
(defun EL:EnsureRoot (/ selected root)
  ;; A standalone session update may define commands before a data root exists.
  (cond
    ((EL:RootValid *EL:Root*) (setq *EL:Root* (EL:NormalizeRoot *EL:Root*)))
    ((and *EL:PackageMarker* (or *EL:StartupAttempted* *EL:StartupError*))
      ;; Date: 2026-10-15. A failed automatic startup must not reopen the
      ;; legacy file picker on ELSTAT. Manual relocation belongs to ELROOT.
      (setq *EL:Root* nil)
      (princ (strcat "\n插件目录尚未就绪，请修复加载错误后重新加载；如需切换目录，请主动运行 ELROOT。"
        (if *EL:StartupError* (strcat "\n初始化原因：" (vl-string-translate "/" "\\" *EL:StartupError*)) ""))) nil)
    (T
      (setq *EL:Root* nil)
      (princ "\n尚未设置有效插件目录，请选择完整包内的 src/load.lsp。")
      (setq selected (EL:PerfInput 'getfiled (list "请选择本包内的 src/load.lsp" "" "lsp" 0)))
      (cond
        ((not selected) (princ "\n未选择插件目录，本次操作已停止。") nil)
        ((setq root (EL:RootFromLoad selected))
          (setq *EL:Root* root)
          (princ (strcat "\n插件目录已设置：" root)) root)
        (T (princ "\n请选择 src/load.lsp，并保留完整的 src、ui、assets、templates 目录。") nil)))))
(defun EL:ConfigPath (id / root)
  (if (and (equal (type id) 'STR) (/= id "")
           (setq root (EL:NormalizeRoot *EL:Root*)))
    (strcat *EL:LiteDataRoot* "config/drawing-" (EL:Hash id) ".eld")))
(defun EL:DefaultConfig (id)
  (list (cons 'version 2) (cons 'roles nil) (cons 'exits nil) (cons 'drawing id) (cons 'revision 0)
        (cons 'calibrated nil) (cons 'units "mm") (cons 'params nil)
        (cons 'wire-layers nil) (cons 'panel-layers nil) (cons 'device-layers nil)
        (cons 'leader-layers nil) (cons 'panel-names nil) (cons 'device-names nil)
        (cons 'leader-names nil) (cons 'layer-pairs nil) (cons 'gap-pairs nil)
        (cons 'leader-pairs nil) (cons 'powers nil) (cons 'template nil)))
(defun EL:ConfigValid (cfg id / ok k pair seen)
  (setq ok (and (EL:OnlyKeys cfg '(version drawing revision calibrated units params
        preset-scoped wire-styles auto-panel concentrated-trunk circuit-starts wire-layers panel-layers device-layers leader-layers panel-names device-names
        leader-names layer-pairs gap-pairs leader-pairs powers template roles exits))
        (member (EL:Get 'version cfg) '(1 2)) (equal (EL:Get 'drawing cfg) id)
        (equal (type (EL:Get 'revision cfg)) 'INT) (>= (EL:Get 'revision cfg) 0)
        (or (not (EL:Get 'params cfg)) (EL:ParamsValid (EL:Get 'params cfg)))
        (or (not (EL:Get 'calibrated cfg))
          (and (equal (EL:Get 'calibrated cfg) T) (EL:ParamsValid (EL:Get 'params cfg))
               (equal (type (EL:Get 'units cfg)) 'STR) (/= (EL:Get 'units cfg) "")))))
  (foreach k '(wire-layers panel-layers device-layers leader-layers panel-names device-names leader-names)
    (if (not (EL:Strings (EL:Get k cfg))) (setq ok nil)))
  ;; Date: 2026-10-10. Optional inferred style and exact panel-contact identity.
  (if (and (EL:Get 'circuit-starts cfg)
      (not (and (EL:Get 'auto-panel cfg) (not (EL:Get 'concentrated-trunk cfg))
        (EL:CircuitStartsValid (EL:Get 'circuit-starts cfg))))) (setq ok nil))
  (if (and (EL:Get 'auto-panel cfg) (not (equal (type (EL:Get 'auto-panel cfg)) 'STR))) (setq ok nil))
  (if (and (EL:Get 'concentrated-trunk cfg)
      (or (not (equal (type (EL:Get 'concentrated-trunk cfg)) 'STR))
          (equal (EL:Get 'concentrated-trunk cfg) "") (not (EL:Get 'auto-panel cfg)))) (setq ok nil))
  (foreach pair (EL:Get 'wire-styles cfg)
    (if (not (and (EL:Strings pair) (= (length pair) 2))) (setq ok nil)))
  (foreach pair (EL:Get 'layer-pairs cfg)
    (if (not (and (EL:Strings pair) (= (length pair) 2))) (setq ok nil)))
  (foreach pair (EL:Get 'gap-pairs cfg)
    (if (not (and (EL:OnlyKeys pair '(a b source signature params drawing date exception a-state b-state rules))
                  (equal (EL:Get 'source pair) 'manual) (equal (EL:Get 'drawing pair) id)
                  (= (length (EL:Get 'a pair)) 2) (= (length (EL:Get 'b pair)) 2)
                  (equal (type (car (EL:Get 'a pair))) 'STR) (equal (type (car (EL:Get 'b pair))) 'STR)
                  (member (cadr (EL:Get 'a pair)) '(start end)) (member (cadr (EL:Get 'b pair)) '(start end))
                  (equal (type (EL:Get 'signature pair)) 'STR) (EL:ParamsValid (EL:Get 'params pair)))) (setq ok nil)))
  (foreach pair (EL:Get 'leader-pairs cfg)
    (if (not (and (EL:OnlyKeys pair '(a b a-state b-state drawing date))
                  (equal (EL:Get 'drawing pair) id) (equal (type (EL:Get 'a pair)) 'STR)
                  (equal (type (EL:Get 'b pair)) 'STR) (equal (type (EL:Get 'a-state pair)) 'STR)
                  (equal (type (EL:Get 'b-state pair)) 'STR))) (setq ok nil)))
  (foreach pair (EL:Get 'roles cfg)
    (if (or (not (EL:RoleShape pair)) (member (EL:Get 'identity pair) seen)) (setq ok nil))
    (setq seen (cons (EL:Get 'identity pair) seen)))
  (if (and (equal (EL:Get 'version cfg) 1) (or (EL:Get 'roles cfg) (EL:Get 'exits cfg))) (setq ok nil))
  (foreach pair (EL:Get 'exits cfg) (if (not (EL:ExitShape pair)) (setq ok nil)))
  (foreach pair (EL:Get 'powers cfg) (if (not (EL:PowerShape pair)) (setq ok nil)))
  (if (and (EL:Get 'template cfg) (not (EL:TemplateValid (EL:Get 'template cfg)))) (setq ok nil))
  ok)
(defun EL:LoadValidGapPairs (cfg snapshot / valid issues pair a b rec)
  (foreach pair (EL:Get 'gap-pairs cfg)
    (setq a (EL:By 'key (EL:Get 'a pair) (EL:Get 'ends snapshot))
          b (EL:By 'key (EL:Get 'b pair) (EL:Get 'ends snapshot)))
    (if (and a b (equal (EL:Get 'drawing pair) (EL:Get 'drawing cfg))
             (equal (EL:Get 'signature pair) (EL:Get 'signature snapshot))
             (equal (EL:Get 'params pair) (EL:Get 'params cfg))
             (equal (EL:Get 'rules pair) (EL:Get 'roles cfg))
             (not (EL:Get 'occupied a)) (not (EL:Get 'occupied b)))
      (setq valid (cons pair valid))
      (foreach rec (list (car (EL:Get 'a pair)) (car (EL:Get 'b pair)))
        (setq issues (cons (EL:Issue 'STALE_PAIR rec pair) issues)))))
  (list (cons 'pairs valid) (cons 'issues issues)))
(defun EL:ReadData (path / file line textdata result)
  ;; READ parses data; EVAL/LOAD is never used for configuration.
  (if (setq file (open path "r"))
    (progn
      (setq textdata "")
      (while (setq line (read-line file)) (setq textdata (strcat textdata line "\n")))
      (close file)
      (setq result (vl-catch-all-apply 'read (list textdata)))
      (if (not (vl-catch-all-error-p result)) result))))
(defun EL:WriteData (path data / file tmp backup result)
  ;; Same-directory replacement; restore the previous version on rename failure.
  (setq tmp (strcat path ".tmp") backup (strcat path ".bak"))
  (if (setq file (open tmp "w"))
    (progn
      (write-line (vl-prin1-to-string data) file) (close file)
      (if (findfile backup) (vl-file-delete backup))
      (if (findfile path) (setq result (vl-file-rename path backup)) (setq result T))
      (if result
        (progn
          (setq result (vl-file-rename tmp path))
          (if result (if (findfile backup) (vl-file-delete backup))
            (if (findfile backup) (vl-file-rename backup path)))))
      (if (findfile tmp) (vl-file-delete tmp)) result)))
(defun EL:LoadConfig (/ id path raw checked)
  (if (setq id (EL:DrawingID))
    (if (and (EL:EnsureRoot) (setq path (EL:ConfigPath id)))
      (if (not (findfile path)) (EL:DefaultConfig id)
        (progn
          (setq raw (EL:ReadData path)
                checked (vl-catch-all-apply 'EL:ConfigValid (list raw id)))
          (if (and (not (vl-catch-all-error-p checked)) checked) (EL:MigrateBoxConfig (EL:UpgradeGapConfig raw))
            (progn (princ (strcat "\n配置失效，请核对或用 ELSETUP 重新采样：" path)) nil)))))
    (progn (princ "\n请先保存 DWG，再建立图纸配置。") nil)))
(defun EL:SaveConfig (cfg / id next path)
  (setq id (EL:DrawingID) next (EL:Put 'revision (1+ (EL:Get 'revision cfg)) cfg))
  (if (and (EL:ConfigValid next id) (EL:EnsureRoot)
           (setq path (EL:ConfigPath id)) (EL:WriteData path next)) next
    (progn (princ "\n配置未保存；检查配置字段和目录写入权限。") nil)))
(defun EL:RolesReady (cfg / ok key name)
  (setq ok T)
  (foreach key '(wire-layers panel-layers device-layers leader-layers)
    (foreach name (EL:Get key cfg)
      (if (not (tblsearch "LAYER" name)) (progn (setq ok nil) (princ (strcat "\n配置图层不存在：" name))))))
  (foreach key '(panel-names device-names leader-names)
    (foreach name (EL:Get key cfg)
      (if (not (tblsearch "BLOCK" name)) (progn (setq ok nil) (princ (strcat "\n配置块定义不存在：" name))))))
  (and ok (EL:Get 'wire-layers cfg)
    (or (EL:Get 'panel-layers cfg) (vl-some '(lambda (r) (equal (EL:Get 'role r) 'panel)) (EL:Get 'roles cfg)))
    (or (EL:Get 'device-layers cfg) (vl-some '(lambda (r) (equal (EL:Get 'role r) 'device)) (EL:Get 'roles cfg)))))
(defun EL:SetupConfig (/ cfg id path backup)
  (setq id (EL:DrawingID) cfg (EL:LoadConfig))
  (if (and id (not cfg) (setq path (EL:ConfigPath id)))
    (progn
      (setq backup (strcat path ".invalid-" (rtos (getvar "CDATE") 2 8)))
      (if (or (not (findfile path)) (vl-file-copy path backup))
        (progn (princ (strcat "\n失效配置已保留到 " backup "；重新采样建立配置。")) (setq cfg (EL:DefaultConfig id))))))
  (if cfg
    (progn
      (foreach id '(panel-layers wire-layers device-layers panel-names device-names) (setq cfg (EL:Put id nil cfg)))
      (EL:Put 'calibrated nil cfg))))
(defun EL:EffectiveName (entity / obj)
  (setq obj (vlax-ename->vla-object entity))
  (if (vlax-property-available-p obj 'EffectiveName) (vla-get-EffectiveName obj)
    (cdr (assoc 2 (entget entity)))))
(defun EL:Role (layer name cfg / panel leader device)
  (setq panel (and (member layer (EL:Get 'panel-layers cfg)) (member name (EL:Get 'panel-names cfg)))
        leader (and (member layer (EL:Get 'leader-layers cfg)) (member name (EL:Get 'leader-names cfg)))
        device (and (member layer (EL:Get 'device-layers cfg)) (member name (EL:Get 'device-names cfg))))
  (cond ((and panel leader) 'ambiguous) (leader 'leader) (panel 'panel) (device 'device) (T 'unknown)))
(defun EL:HighlightPick (entity / result)
  (if (and entity (not (member entity *EL:PickHighlights*)))
    (progn
      (setq result (vl-catch-all-apply 'redraw (list entity 3)))
      (if (not (vl-catch-all-error-p result))
        (setq *EL:PickHighlights* (cons entity *EL:PickHighlights*)))))
  entity)
(defun EL:UnhighlightPick (entity)
  (if (member entity *EL:PickHighlights*)
    (progn
      (vl-catch-all-apply 'redraw (list entity 4))
      (setq *EL:PickHighlights* (vl-remove entity *EL:PickHighlights*))))
  (princ))
(defun EL:ClearPickHighlights (/ entity)
  ;; Always finish the remaining cleanup, even if an entity was deleted.
  (foreach entity *EL:PickHighlights*
    (vl-catch-all-apply 'redraw (list entity 4)))
  (setq *EL:PickHighlights* nil)
  (princ))
(defun EL:PickEntity (prompt / pick data)
  (if (setq pick (EL:PerfInput 'entsel (list prompt)))
    (progn
      (EL:HighlightPick (car pick))
      (setq data (entget (car pick)))
      (princ (strcat "\n已拾取：" (cond ((cdr (assoc 0 data))) (T "未知类型"))
        "；图层：" (cond ((cdr (assoc 8 data))) (T "未知"))
        "；句柄：" (cond ((cdr (assoc 5 data))) (T "未知"))))))
  pick)
(defun EL:Sample (cfg role prompt / pick data layer name lk nk)
  (if (setq pick (EL:PickEntity prompt))
    (progn
      (setq data (entget (car pick)) layer (cdr (assoc 8 data)))
      (if (if (equal role 'wire) (member (cdr (assoc 0 data)) '("LINE" "LWPOLYLINE"))
            (equal (cdr (assoc 0 data)) "INSERT"))
        (progn
          (setq lk (read (strcat (vl-symbol-name role) "-LAYERS")))
          (setq cfg (EL:Put lk (EL:Unique (cons layer (EL:Get lk cfg))) cfg))
          (if (not (equal role 'wire))
            (progn
              (setq name (EL:EffectiveName (car pick)) nk (read (strcat (vl-symbol-name role) "-NAMES")))
              (setq cfg (EL:Put nk (EL:Unique (cons name (EL:Get nk cfg))) cfg))))
          cfg)
        (progn (princ "\n样本类型错误，未保存。") nil)))))
(defun EL:SuggestedParams ()
  ;; Strict gap policy; contact tolerances are separate from gap alignment.
  '((eps_touch . 0.1) (eps_boundary . 0.1) (eps_device . 0.01) (eps_perp . 0.0)
      (eps_z . 0.0) (theta_max . 0.0) (R0 . 20.0) (Dmax . 2000.0) (gap_rule . 10)))
(defun EL:GapParams (p)
  (if (not (EL:ParamsValid p)) (EL:SuggestedParams)
    (progn
      ;; Date: 2026-10-14. Legacy configs gain a separate device XY tolerance.
      (if (not (assoc 'eps_device p)) (setq p (EL:Put 'eps_device 0.01 p)))
      (if (not (equal (EL:Get 'gap_rule p) 10))
        (setq p (EL:Put 'Dmax 2000.0 (EL:Put 'R0 20.0 p))))
      (EL:Put 'gap_rule 10 (EL:Put 'eps_perp 0.0 (EL:Put 'theta_max 0.0 (EL:Put 'eps_z 0.0 p)))))))
(defun EL:FixedRecognitionParams (cfg / p saved)
  ;; Date: 2026-10-14. Keep automatic wire/gap defaults, inherit drawing contact setting.
  (setq p (EL:GapParams (EL:SuggestedParams)) saved (EL:Get 'params cfg))
  (if (and (assoc 'eps_device saved) (EL:NonNegative (EL:Get 'eps_device saved)))
    (setq p (EL:Put 'eps_device (EL:Get 'eps_device saved) p))) p)
(defun EL:UpgradeGapConfig (cfg / p)
  (if (and (setq p (EL:Get 'params cfg)) (not (equal (EL:Get 'gap_rule p) 10)))
    (progn
      (princ "\n断口规则已升级：默认搜索 2000 mm，仅共线、相向、同高程；已接设备的整条导线不参与。")
      (setq cfg (EL:Put 'params (EL:GapParams p) (EL:Put 'calibrated nil cfg)))))
  cfg)
(defun EL:ParamLabel (key)
  (cond ((equal key 'eps_touch) "线端允许接触偏差")
        ((equal key 'eps_boundary) "配电箱与候选轮廓允许偏差")
        ((equal key 'eps_device) "设备真实轮廓接触容差")
        ((equal key 'eps_perp) "断口横向允许偏差")
        ((equal key 'eps_z) "导线高程允许偏差")
        ((equal key 'theta_max) "断口方向允许偏差")
        ((equal key 'R0) "断口初始搜索距离")
        ((equal key 'Dmax) "断口最大搜索距离") (T (vl-symbol-name key))))
(defun EL:ParamUnit (key) (if (equal key 'theta_max) "rad（弧度）" "mm"))
(defun EL:ShowParams (p / key)
  (princ "\n接线与断口识别参数：")
  (foreach key '(eps_touch eps_boundary eps_device Dmax)
    (princ (strcat "\n  " (EL:ParamLabel key) " = " (rtos (EL:Get key p) 2 4)
      " " (EL:ParamUnit key))))
  (princ "\n接触偏差只用于识别实际接线；断口固定按共线、相向、同高程匹配。")
  (princ "\n整条导线任一端接了设备或配电箱，就不参与断口搜索；非共线交叉线忽略。"))
(defun EL:SameParams (a b / same key)
  (if (and (EL:ParamsValid a) (EL:ParamsValid b))
    (progn
      (setq same T)
      (foreach key '(eps_touch eps_boundary eps_device eps_perp eps_z theta_max R0 Dmax gap_rule)
        (if (not (equal (EL:Get key a) (EL:Get key b))) (setq same nil)))
      same)))
(defun EL:InputParamValues (defaults / p x key)
  (setq p (EL:GapParams defaults))
  (foreach key '(eps_touch eps_boundary eps_device Dmax)
    (setq x (getreal (strcat "\n" (EL:ParamLabel key) "（" (EL:ParamUnit key) "） <"
      (rtos (EL:Get key p) 2 4) ">，回车保留此值: ")))
    (if x (setq p (EL:Put key x p))))
  (if (EL:ParamsValid p) (if (EL:SameParams p defaults) defaults p)
    (progn (princ "\n参数范围无效，未保存。") nil)))
(defun EL:InputParams () (EL:InputParamValues (EL:SuggestedParams)))
(defun EL:Choice12 (prompt default / choice)
  (while (not choice)
    (initget 6)
    (setq choice (getint prompt))
    (cond ((not choice) (setq choice default))
          ((not (member choice '(1 2)))
            (princ "\n请输入 1 或 2，也可直接回车采用默认选项。") (setq choice nil))))
  choice)
(defun EL:ChooseParams (current / p)
  (setq p (EL:GapParams current))
  (EL:ShowParams p)
  (if (= (EL:Choice12 "\n参数选择：1=直接使用以上数值，2=逐项调整 <1，回车直接使用>: " 1) 2)
    (EL:InputParamValues p) p))
(defun EL:ConfirmParams ()
  (princ "\n请核对正常接线的小偏差，并用 ELGAPTEST 检查典型断口、最大断口及邻近回路。")
  (princ "\n还未核对时先保存草稿；断口对象正确、没有误选邻近回路后，再启用统计。")
  (= (EL:Choice12 "\n识别参数确认：1=已核对，启用统计，2=未核对，只保存草稿 <2，回车保存草稿>: " 2) 1))
(defun EL:SetupSamples (/ cfg reuse)
  (setq cfg (EL:LoadConfig))
  (if (and cfg (EL:Get 'panel-layers cfg) (EL:Get 'wire-layers cfg) (EL:Get 'device-layers cfg))
    (progn
      (initget "Reuse Resample")
      (setq reuse (not (equal (getkword "\n已有采样 [Reuse沿用/Resample重新拾取] <Reuse>: ") "Resample")))))
  (if (and (not reuse) (or cfg (EL:RootValid *EL:Root*)))
    (progn
      (setq cfg (EL:SetupConfig))
      (if cfg (setq cfg (EL:Sample cfg 'panel "\n拾取配电箱图块样本: ")))
      (if cfg (setq cfg (EL:Sample cfg 'wire "\n拾取导线样本（直线或开放多段线）: ")))
      (if cfg (setq cfg (EL:Sample cfg 'device "\n拾取灯具或标志图块样本: ")))))
  cfg)
(defun c:ELSETUP (/ *error* cfg p confirmed)
  (defun *error* (msg)
    (EL:ClearPickHighlights)
    (if msg (princ (strcat "\n设置已取消，拾取亮显已清理：" msg))) (princ))
  (EL:ClearPickHighlights)
  (princ "\n设置用于识别配电箱、导线和设备；完成后另行运行 ELSTAT 统计。")
  (princ "\n单位固定为 mm（毫米），无需输入或确认。")
  (if (setq cfg (EL:SetupSamples))
    (progn
      (setq p (EL:ChooseParams (EL:Get 'params cfg)))
      (if p
        (progn
          (setq confirmed (and (EL:Get 'calibrated cfg) (equal (EL:Get 'units cfg) "mm")
                               (EL:SameParams p (EL:Get 'params cfg)))
                cfg (EL:Put 'params p cfg) cfg (EL:Put 'units "mm" cfg))
          (if confirmed (princ "\n采样和识别参数未改变，沿用已核对的设置。")
            (setq confirmed (EL:ConfirmParams)))
          (setq cfg (EL:Put 'calibrated confirmed cfg))
          (if (EL:SaveConfig cfg)
            (if (EL:Get 'calibrated cfg)
              (princ "\n设置已确认并保存。下一步：输入 ELSTAT，拾取要统计的配电箱。")
              (princ "\n采样和参数草稿已保存。下一步：运行 ELGAPTEST 检查断口；核对后再运行 ELSETUP，沿用采样及参数，最后输入 1 启用统计。"))))))
    (princ "\n采样未完成，本次设置未保存。请用 ELSETUP 重新拾取样本。"))
  (EL:ClearPickHighlights)
  (princ))
(defun c:ELSAMPLE (/ *error* cfg role)
  (defun *error* (msg)
    (EL:ClearPickHighlights)
    (if msg (princ (strcat "\n采样已取消，拾取亮显已清理：" msg))) (princ))
  (EL:ClearPickHighlights)
  (if (setq cfg (EL:LoadConfig))
    (progn
      (initget "Panel Wire Device Leader")
      (if (setq role (getkword "\n追加样本角色 [Panel/Wire/Device/Leader]: "))
        (if (setq cfg (EL:Sample cfg (read role) "\n拾取该角色样本: ")) (EL:SaveConfig cfg)))))
  (EL:ClearPickHighlights)
  (princ))
(princ)

(defun EL:RoleShape (row)
  (and (EL:OnlyKeys row '(identity role confirmed)) (equal (EL:Get 'confirmed row) T)
    (EL:IdentityValid (EL:Get 'identity row))
    (member (EL:Get 'role row) '(device panel leader ignore junction))))
(defun EL:ExitShape (row / valid key)
  (setq valid (and (EL:OnlyKeys row '(panel signature layers roles keys scope-excluded policy))
    (equal (EL:Get 'policy row) 1) (equal (type (EL:Get 'panel row)) 'STR)
    (equal (type (EL:Get 'signature row)) 'STR) (EL:Strings (EL:Get 'layers row))
    (listp (EL:Get 'keys row)) (member (EL:Get 'scope-excluded row) '(nil T))))
  (foreach key (EL:Get 'keys row)
    (if (not (and (= (length key) 2) (equal (type (car key)) 'STR) (member (cadr key) '(start end)))) (setq valid nil)))
  valid)
(defun EL:RememberExits (cfg panel snapshot selected excluded / row old)
  (setq row (list (cons 'panel panel) (cons 'signature (EL:Get 'signature snapshot))
    (cons 'policy 1) (cons 'layers (EL:Get 'wire-layers cfg)) (cons 'roles (EL:Get 'roles cfg))
    (cons 'keys (mapcar '(lambda (s) (EL:Get 'key s)) selected)) (cons 'scope-excluded excluded))
    old (EL:By 'panel panel (EL:Get 'exits cfg)))
  (EL:Put 'exits (if old (subst row old (EL:Get 'exits cfg)) (cons row (EL:Get 'exits cfg))) cfg))
(defun EL:ReusableExits (cfg panel snapshot / row)
  (setq row (EL:By 'panel panel (EL:Get 'exits cfg)))
  (if (and (EL:ExitShape row) (equal (EL:Get 'signature row) (EL:Get 'signature snapshot))
       (equal (EL:Get 'layers row) (EL:Get 'wire-layers cfg)) (equal (EL:Get 'roles row) (EL:Get 'roles cfg))) row))
(defun EL:MigrateBoxConfig (cfg)
  (if (equal (EL:Get 'version cfg) 1)
    (progn
      (princ "\n整箱模式已升级：保留功率和模板，旧断口配对失效，请重新核对。")
      (setq cfg (EL:Put 'version 2 (EL:Put 'gap-pairs nil (EL:Put 'roles nil (EL:Put 'exits nil cfg)))))))
  cfg)

(defun EL:IdentityValid (identity)
  (and (listp identity) (= (length identity) 3) (equal (type (car identity)) 'STR)
    (listp (cadr identity)) (equal (type (caddr identity)) 'STR)))
(defun EL:PutRole (cfg identity role / row old)
  (setq row (list (cons 'identity identity) (cons 'role role) (cons 'confirmed T))
        old (EL:By 'identity identity (EL:Get 'roles cfg)))
  (EL:Put 'roles (if old (subst row old (EL:Get 'roles cfg)) (cons row (EL:Get 'roles cfg))) cfg))

;; Date: 2026-10-13. Fixed circuits share the existing name-based identity.
(defun EL:FixedBlockIdentity (name) (list name nil "block-name-v1"))
(defun EL:JunctionName (name cfg)
  (equal (EL:Get 'role (EL:By 'identity (EL:FixedBlockIdentity name) (EL:Get 'roles cfg))) 'junction))
(defun EL:FixedBlockRole (block panel cfg)
  (cond ((equal (EL:Get 'id block) panel) 'panel)
    ((or (EL:JunctionName (EL:Get 'name block) cfg) (and (not cfg) (equal (EL:Get 'role block) 'junction))) 'junction)
    (T 'device)))
(defun EL:JunctionSamples (cfg names remove-role / name identity)
  (foreach name (EL:Unique names)
    (setq identity (EL:FixedBlockIdentity name))
    (if remove-role
      (setq cfg (EL:Put 'roles (vl-remove-if '(lambda (row)
        (and (equal (EL:Get 'identity row) identity) (equal (EL:Get 'role row) 'junction))) (EL:Get 'roles cfg)) cfg))
      (setq cfg (EL:PutRole cfg identity 'junction)))) cfg)
;; Date: 2026-10-13. Drawing classification overrides old saved system config.
(defun EL:CurrentJunctionConfig (cfg / path saved checked junctions)
  (if (and *EL:Root* (setq path (EL:ConfigPath (EL:Get 'drawing cfg))) (findfile path))
    (progn
      (setq saved (EL:ReadData path) checked (vl-catch-all-apply 'EL:ConfigValid (list saved (EL:Get 'drawing cfg))))
      (EL:Require (and (not (vl-catch-all-error-p checked)) checked) "本图配置无法读取，接线盒分类未确认，请修复配置后重新统计。")
      ;; Date: 2026-10-14. Current drawing contact tolerance also overrides old system records.
      (if (assoc 'eps_device (EL:Get 'params saved))
        (setq cfg (EL:Put 'params (EL:Put 'eps_device (EL:Get 'eps_device (EL:Get 'params saved))
          (EL:Get 'params cfg)) cfg)))
      (setq junctions (vl-remove-if-not '(lambda (row) (equal (EL:Get 'role row) 'junction)) (EL:Get 'roles saved)))
      (setq cfg (EL:Put 'roles (append junctions (vl-remove-if '(lambda (row)
        (or (equal (EL:Get 'role row) 'junction) (EL:By 'identity (EL:Get 'identity row) junctions))) (EL:Get 'roles cfg))) cfg)))) cfg)
(defun EL:JunctionCommandWork (/ cfg action ss i entity data definition names name)
  (if (setq cfg (EL:LoadConfig))
    (progn
      (initget "Set Remove")
      (setq action (getkword "\n接线盒分类 [设置(Set)/取消(Remove)] <Set>: "))
      (princ "\n选择接线盒图块样本，同类型均适用；Enter 完成，Esc 放弃本次修改。")
      (setq ss (ssget '((0 . "INSERT") (410 . "Model"))) i 0)
      (if ss
        (repeat (sslength ss)
          (setq entity (ssname ss i) data (entget entity) i (1+ i)
            definition (tblsearch "BLOCK" (cdr (assoc 2 data))))
          (if (and (equal (cdr (assoc 0 data)) "INSERT") (equal (cdr (assoc 410 data)) "Model")
              (not (EL:ManagedEntity entity)) definition (= 0 (logand 12 (cdr (assoc 70 definition)))))
            (setq names (cons (EL:EffectiveName entity) names)))))
      (if names
        (if (EL:SaveConfig (EL:JunctionSamples cfg names (equal action "Remove")))
          (progn
            (foreach name (EL:Unique names) (princ (strcat "\n" name (if (equal action "Remove") "：已取消接线盒分类" "：已设为接线盒"))))
            (princ "\n请重新运行 ELSTAT；接线盒只连接线路，不计负载。")))
        (princ "\n未选择有效的本地图块，配置未改动。")))))
(defun c:ELJBOX (/ result)
  (setq result (vl-catch-all-apply 'EL:JunctionCommandWork nil))
  (if (vl-catch-all-error-p result) (princ (strcat "\n接线盒分类未完成：" (vl-catch-all-error-message result)))) (princ))

;; Date: 2026-10-12. Shared recognition preset; data only, never LOAD/EVAL.
(defun EL:PresetDefault ()
  (list '(schema . EL_PRESET_V1) '(panel-layers "POWR_电力大设备_E")
    '(panel-names "$equip_U$00000398(Zhangyufeng)")
    '(wire-layers "LITE_应急照明布线_E") '(device-layers "LITE_照明设备_E") '(device-names)))
(defun EL:PresetValid (data / good key)
  (setq good (and (EL:OnlyKeys data '(schema panel-layers panel-names wire-layers device-layers device-names))
    (equal (EL:Get 'schema data) 'EL_PRESET_V1)))
  (foreach key '(panel-layers panel-names wire-layers device-layers device-names)
    (if (or (not (assoc key data)) (not (EL:Strings (EL:Get key data)))
        (and (not (equal key 'device-names)) (not (EL:Get key data)))
        (member "" (EL:Get key data))) (setq good nil))) good)
(defun EL:PresetPath (/ root)
  (setq root (EL:DLRoot))
  (EL:Require root "预设目录不可用。") (strcat root "recognition-preset.eld"))
(defun EL:PresetLoad (/ path data)
  (setq path (EL:PresetPath))
  (if (findfile path)
    (progn (setq data (EL:ReadData path))
      (EL:Require (EL:PresetValid data) "识别预设损坏，原文件已保留；请检查 recognition-preset.eld。") data)
    (EL:PresetDefault)))
(defun EL:PresetSave (data / path)
  (setq path (EL:PresetPath))
  (EL:Require (and (EL:PresetValid data) (EL:DLMkdir (vl-filename-directory path))
    (EL:WriteData path data) (equal (EL:ReadData path) data)) "预设保存或回读失败，不能确认保存成功。")
  (princ (strcat "\n预设已保存：" path)) data)
(defun EL:PresetConfig (cfg / preset key)
  (setq preset (EL:PresetLoad))
  (foreach key '(panel-layers panel-names wire-layers device-layers device-names)
    (setq cfg (EL:Put key (EL:Get key preset) cfg)))
  (EL:Put 'preset-scoped T cfg))
(defun EL:PresetMember (value values)
  (and (equal (type value) 'STR) (member (strcase value) (mapcar 'strcase values))))
(defun EL:PresetBlockAllowed (entity data cfg)
  (or (not (EL:Get 'preset-scoped cfg))
    (EL:PresetBlockNameAllowed (EL:EffectiveName entity) data cfg)))
(defun EL:PresetBlockNameAllowed (name data cfg)
  ;; Date: 2026-10-15. One effective-name lookup serves every role predicate.
  (or (not (EL:Get 'preset-scoped cfg))
    (EL:JunctionName name cfg)
    (and (EL:PresetMember (cdr (assoc 8 data)) (EL:Get 'panel-layers cfg))
      (EL:PresetMember name (EL:Get 'panel-names cfg)))
    (and (EL:PresetMember (cdr (assoc 8 data)) (EL:Get 'device-layers cfg))
      (EL:PresetMember name (EL:Get 'device-names cfg)))))
(defun EL:PresetReady (panel cfg / data names message snapshot)
  (if (EL:Get 'preset-scoped cfg)
    (progn (setq data (entget panel))
      (EL:Require (and (EL:PresetMember (cdr (assoc 8 data)) (EL:Get 'panel-layers cfg))
        (EL:PresetMember (EL:EffectiveName panel) (EL:Get 'panel-names cfg)))
        "配电箱与预设不匹配，请运行 ELPRESET 修改图层或块名。")
      ;; Device picking is a separate library action; statistics never starts it.
      (setq snapshot (EL:DLSnapshot)
        names (EL:Unique (append (EL:Get 'device-names cfg) (EL:DLRecognitionNames snapshot))))
      (if names (setq cfg (EL:Put 'device-names names cfg))
        (progn
          (setq message (if (and (not snapshot) *EL:DLError*)
            (strcat "设备库暂时无法读取：" *EL:DLError* "；请打开完整设备库检查后重新统计。")
            "尚无已登记设备，请打开设备库，点击“拾取设备入库”，再拾取配电箱统计。"))
          (EL:LogEvent "DEVICE_LIBRARY_PICK_REQUIRED" (list (cons 'message message)))
          (princ (strcat "\n" message)) (EL:PerfInput 'alert (list message)) (setq cfg nil))))) cfg)
(defun EL:PresetEscape (name / out char)
  (setq out "")
  (foreach char (vl-string->list name)
    (setq char (chr char) out (strcat out (if (member char '("`" "#" "@" "." "*" "?" "~" "[" "]" "-" ",")) "`" "") char))) out)
(defun EL:PresetSelection (cfg types keys / layers key name filter)
  (setq filter (list '(410 . "Model") (cons 0 types)))
  (if (EL:Get 'preset-scoped cfg)
    (progn
      (foreach key keys (setq layers (append layers (EL:Get key cfg))))
      (setq filter (append filter (list '(-4 . "<OR"))))
      (foreach name (EL:Unique layers) (setq filter (append filter (list (cons 8 (EL:PresetEscape name))))))
      ;; Registered junctions can be on their own layer; names are checked after selection.
      (if (and (member types '("INSERT" "INSERT,LINE,LWPOLYLINE"))
          (vl-some '(lambda (row) (equal (EL:Get 'role row) 'junction)) (EL:Get 'roles cfg)))
        (setq filter (append filter (list '(0 . "INSERT")))))
      (setq filter (append filter (list '(-4 . "OR>"))))))
  (ssget "_X" filter))
(defun EL:PresetEditWork (/ data key value)
  (setq data (EL:PresetLoad))
  (princ "\n设置识别预设：Enter 保留原值，Esc 取消本次修改。")
  (foreach key '(panel-layers panel-names wire-layers device-layers)
    (setq value (getstring T (strcat "\n" (cond ((equal key 'panel-layers) "配电箱图层")
      ((equal key 'panel-names) "配电箱块名") ((equal key 'wire-layers) "导线图层") (T "设备图层"))
      " <" (car (EL:Get key data)) ">：")))
    (if (/= value "") (setq data (EL:Put key (list value) data))))
  (EL:PresetSave data)
  (princ "\n识别预设已保存；设备请在 ELDEVLIB 中点击“拾取设备入库”。"))
(defun EL:PresetCommand (function / result)
  (setq result (vl-catch-all-apply function nil))
  (if (vl-catch-all-error-p result) (princ (strcat "\n操作未完成：" (vl-catch-all-error-message result)))) (princ))
(defun c:ELPRESET () (EL:PresetCommand 'EL:PresetEditWork))
(defun c:ELDEVPICK () (EL:PresetCommand 'EL:DLUIPickOpen))

;; Date: 2026-10-11. Revision: 2026.10.11.3. Standalone native HLBH batch numbering.
;; Source: UTF-8. Load only the separately exported GB2312 file in CAD2020.
(vl-load-com)

(defun HLBN:Get (key record) (cdr (assoc key record)))
(defun HLBN:Log (stage data / stream path)
  (setq path (strcat (getvar "TEMPPREFIX") "HLPLBH-debug.log"))
  (setq stream (vl-catch-all-apply 'open (list path "a")))
  (if (and stream (not (vl-catch-all-error-p stream)))
    (progn
      (vl-catch-all-apply 'write-line (list
        (strcat (rtos (getvar "CDATE") 2 6) " " stage " " (vl-prin1-to-string data)) stream))
      (vl-catch-all-apply 'close (list stream))))
  path)
(defun HLBN:Check (condition message)
  (if (not condition) (progn (setq hlbn-failure message) (princ (strcat "\n" message)) (exit))) condition)

(defun HLBN:NumberParts (text / index split digits number digit valid)
  (if (equal (type text) 'STR)
    (progn
      (setq text (vl-string-trim " \t\r\n" text) index (strlen text))
      (while (and (> index 0) (<= 48 (ascii (substr text index 1)))
                  (>= 57 (ascii (substr text index 1))))
        (setq index (1- index)))
      (setq split index digits (substr text (1+ split)) number 0 valid (> (strlen digits) 0) index 1)
      (while (and valid (<= index (strlen digits)))
        (setq digit (- (ascii (substr digits index 1)) 48))
        (if (or (> number 214748364) (and (= number 214748364) (> digit 7)))
          (setq valid nil)
          (setq number (+ (* number 10) digit)))
        (setq index (1+ index)))
      (if (and valid (<= (strlen text) 256)
               (not (vl-string-search "\\" text)) (not (vl-string-search "{" text))
               (not (vl-string-search "}" text)))
        (list (substr text 1 split) number (strlen digits))))))
(defun HLBN:NumberAt (parts index / digits)
  (if (and parts (>= index 0) (<= index (- 2147483647 (cadr parts))))
    (progn
      (setq digits (itoa (+ (cadr parts) index)))
      (while (< (strlen digits) (caddr parts)) (setq digits (strcat "0" digits)))
      (strcat (car parts) digits))))

(defun HLBN:CurveRow (entity / data kind start end length point closed)
  (setq data (entget entity) kind (cdr (assoc 0 data)))
  (if (and kind (or (member kind '("LINE" "LWPOLYLINE" "POLYLINE"))
                    (and (vl-string-search "TCH" (strcase kind))
                         (vl-string-search "WIRE" (strcase kind))))
           (not (and (equal kind "POLYLINE") (assoc 70 data)
                     (> (logand 88 (cdr (assoc 70 data))) 0))))
    (progn
      (setq closed (vlax-curve-isClosed entity))
      (if (not closed)
        (progn
          (setq start (vlax-curve-getStartPoint entity) end (vlax-curve-getEndPoint entity)
            length (vlax-curve-getDistAtParam entity (vlax-curve-getEndParam entity)))
          (if (and start end (numberp length) (> length 0.000001))
            (progn
              (setq point (vlax-curve-getPointAtDist entity (/ length 2.0)))
              (if point
                (list (cons 'entity entity) (cons 'handle (cdr (assoc 5 data)))
                  (cons 'pick (trans point 0 1))
                  (cons 'start (trans start 0 1)) (cons 'end (trans end 0 1)))))))))))
(defun HLBN:Rows (selection / index row rows skipped)
  (setq index 0 skipped 0)
  (repeat (sslength selection)
    (setq row (vl-catch-all-apply 'HLBN:CurveRow (list (ssname selection index))))
    (if (or (vl-catch-all-error-p row) (not row))
      (progn
        (setq skipped (1+ skipped))
        (HLBN:Log "SKIPPED" (list (entget (ssname selection index))
          (if (vl-catch-all-error-p row) (vl-catch-all-error-message row) "unsupported or closed"))))
      (setq rows (cons row rows)))
    (setq index (1+ index)))
  (list rows skipped))
(defun HLBN:RowBefore (a b / p q)
  (setq p (HLBN:Get 'pick a) q (HLBN:Get 'pick b))
  (cond ((/= (cadr p) (cadr q)) (> (cadr p) (cadr q)))
        ((/= (car p) (car q)) (< (car p) (car q)))
        (T (< (HLBN:Get 'handle a) (HLBN:Get 'handle b)))))
(defun HLBN:DefaultOffset ()
  (if *HLBN:Offset* *HLBN:Offset* '(500.0 500.0 0.0)))
(defun HLBN:Plan (rows parts offset / ordered result index previous plane point row label)
  (HLBN:Check (and (listp offset) (= (length offset) 3)
                  (vl-every 'numberp offset) (= (caddr offset) 0.0)
                  (or (/= (car offset) 0.0) (/= (cadr offset) 0.0)))
    "偏移必须是非零的平面方向，例如右移 500、上移 500。")
  (setq ordered (vl-sort rows 'HLBN:RowBefore) index 0
    plane (caddr (HLBN:Get 'pick (car ordered))))
  (HLBN:Check (<= (1- (length ordered)) (- 2147483647 (cadr parts)))
    "选线数量导致末尾编号超出整数范围，请降低起始编号。")
  (foreach row ordered
    (setq point (HLBN:Get 'pick row) label (HLBN:NumberAt parts index))
    (HLBN:Check (and (equal (caddr point) plane 0.000001)
                    (equal (caddr (HLBN:Get 'start row)) plane 0.000001)
                    (equal (caddr (HLBN:Get 'end row)) plane 0.000001))
      "导线不在当前 UCS 的同一平面，请切换到导线所在的平面 UCS。")
    (HLBN:Check (<= (strlen label) 256) "生成编号超过 256 个字符，请缩短编号前缀。")
    (if previous
      (progn
        (HLBN:Check (not (equal point previous 0.000001))
          "选中了连接点重合的导线，无法可靠区分，请仅选择需要的独立出线。")))
    (setq result (cons (append row (list (cons 'label label) (cons 'offset offset)
      (cons 'landing (mapcar '+ point offset)))) result)
      previous point index (1+ index)))
  (reverse result))

(defun HLBN:Tail (/ entity next)
  (setq entity (entlast))
  (while (and entity (setq next (entnext entity))) (setq entity next)) entity)
(defun HLBN:After (tail / entity result)
  (setq entity (if tail (entnext tail) (entnext)))
  (while entity
    (if (entget entity) (setq result (cons entity result)))
    (setq entity (entnext entity)))
  (reverse result))
(defun HLBN:Snapshot (rows / result row)
  (foreach row rows
    (setq result (cons (list (HLBN:Get 'entity row) (entget (HLBN:Get 'entity row) '("*"))) result)))
  result)
(defun HLBN:SameSources (snapshot / same row)
  (setq same T)
  (foreach row snapshot
    (if (not (equal (cadr row) (entget (car row) '("*")))) (setq same nil))) same)
(defun HLBN:NativeActive (/ names)
  (setq names (getvar "CMDNAMES"))
  ;; Queried only inside our managed HLBH call. ARX commands can use bit 64
  ;; and an internal command name. Some native input loops expose only CMDNAMES.
  (or (> (logand 65 (getvar "CMDACTIVE")) 0)
      (and (equal (type names) 'STR) (vl-string-search "HLBH" (strcase names)))))
(defun HLBN:CommandBusy ()
  ;; Include transparent commands and dialogs before issuing any UNDO tokens.
  (or (> (logand 75 (getvar "CMDACTIVE")) 0) (HLBN:NativeActive)))
(defun HLBN:CommandState ()
  (list (getvar "CMDACTIVE") (getvar "CMDNAMES") (getvar "LASTPROMPT")))
(defun HLBN:PromptKind (prompt / upper)
  (if (equal (type prompt) 'STR)
    (progn
      (setq upper (strcase prompt))
      (cond
        ((or (vl-string-search "UNDO" upper) (vl-string-search "_BEGIN" upper)
             (vl-string-search "_END" upper)) 'history)
        ((and (vl-string-search "导线" prompt) (vl-string-search "选" prompt)) 'wire)
        ((and (vl-string-search "文字" prompt) (vl-string-search "点" prompt)) 'landing)))))
(defun HLBN:PromptIs (stage before / prompt kind stale ok)
  (setq prompt (getvar "LASTPROMPT"))
  (setq kind (HLBN:PromptKind prompt)
    stale (or (not (equal (type prompt) 'STR)) (equal prompt "") (equal prompt before)
      (and (equal (type before) 'STR) (> (strlen before) 0)
           (equal 0 (vl-string-search before prompt)))))
  ;; LASTPROMPT is echoed history, not a native-input stage API. A fresh,
  ;; incompatible prompt still blocks input; cached history is diagnostic only.
  (setq ok (and (HLBN:NativeActive) (= 0 (logand 10 (getvar "CMDACTIVE")))
    (or (equal kind stage) stale (equal kind 'history))))
  (HLBN:Log "PROMPT" (list stage (HLBN:CommandState) before kind stale ok))
  (if (and ok (not (equal kind stage))) (HLBN:Log "PROMPT_CACHED" (list stage prompt)))
  ok)
(defun HLBN:StopNative (/ attempts)
  (setq attempts 0)
  (while (and (< attempts 2) (HLBN:NativeActive))
    ;; HLBH advertises empty input as exit. At the landing prompt the first
    ;; Enter can cancel this row; a second Enter then exits its wire-pick loop.
    (HLBN:Log "CANCEL_BEFORE" (list "Enter" (HLBN:CommandState)))
    (command "")
    (setq attempts (1+ attempts))
    (HLBN:Log "CANCEL_AFTER" (HLBN:CommandState)))
  (not (HLBN:CommandBusy)))

(defun HLBN:TextInfo (entity / object text)
  (setq object (vlax-ename->vla-object entity))
  (if (vlax-property-available-p object 'TextString)
    (progn
      (setq text (vlax-get-property object 'TextString))
      (if (and (equal (type text) 'STR) (> (strlen text) 0))
        (list (cons 'entity entity) (cons 'object object) (cons 'text text)
          (cons 'writable (vlax-property-available-p object 'TextString T))
          (cons 'type (cdr (assoc 0 (entget entity)))))))))
(defun HLBN:SetLabel (entities target / entity info candidates chosen object before after)
  (foreach entity entities
    (setq info (vl-catch-all-apply 'HLBN:TextInfo (list entity)))
    (if (and info (not (vl-catch-all-error-p info))) (setq candidates (cons info candidates))
      (HLBN:Log "TEXT_INTERFACE_UNAVAILABLE" (list (entget entity '("*"))
        (if (vl-catch-all-error-p info) (vl-catch-all-error-message info) nil)))))
  (HLBN:Log "TEXT_CANDIDATES" candidates)
  (HLBN:Check (= (length candidates) 1)
    "HLBH 新增标注没有唯一可读取的 TextString，请提供本工具日志以适配该天正版本。")
  (setq chosen (car candidates) entity (HLBN:Get 'entity chosen) object (HLBN:Get 'object chosen)
    before (HLBN:Get 'type chosen))
  (if (not (equal target (HLBN:Get 'text chosen)))
    (progn
      (HLBN:Check (and (HLBN:NumberParts (HLBN:Get 'text chosen))
                      (not (vl-string-search "\\" (HLBN:Get 'text chosen)))
                      (not (vl-string-search "{" (HLBN:Get 'text chosen))))
        "原生文字包含格式代码或不是回路编号，停止修改以保留天正原样式。")
      (HLBN:Check (HLBN:Get 'writable chosen)
        "该天正标注的 TextString 不可写，无法设置输入编号；本批次将撤销。")
      (vlax-put-property object 'TextString target)
      (vla-Update object)))
  (setq after (HLBN:TextInfo entity))
  (HLBN:Check (and after (equal before (HLBN:Get 'type after))
                  (equal target (HLBN:Get 'text after)))
    "原生标注编号写入后回读不一致，本批次将撤销。")
  (HLBN:Log "LABEL_VERIFIED" (list (cdr (assoc 5 (entget entity))) before target))
  entity)
(defun HLBN:NativeRun (plan / row tail created verified entity landing current before)
  (setq before (getvar "LASTPROMPT"))
  (command "HLBH")
  (HLBN:Check (HLBN:PromptIs 'wire before)
    "HLBH 未进入预期的选导线提示，请确认已加载天正，并保留日志中的实际提示。")
  (foreach row plan
    (HLBN:Check (HLBN:PromptIs 'wire before) "HLBH 选线提示与截图流程不同，停止传入下一条导线。")
    (setq tail (HLBN:Tail))
    (setq current (HLBN:Get 'pick row) landing (HLBN:Get 'landing row))
    (HLBN:Log "ROW_BEGIN" (list (HLBN:Get 'handle row) (HLBN:Get 'label row)
      (HLBN:Get 'pick row) landing))
    ;; Native HLBH takes two point inputs. An (entity pick) list is not a point.
    (setq before (getvar "LASTPROMPT"))
    (HLBN:Log "INPUT_POINT" (list 'wire (HLBN:Get 'handle row) current))
    (command current)
    (HLBN:Log "INPUT_RETURN" (list 'wire (HLBN:CommandState)))
    ;; A native mark created on the first point belongs to this same row.
    (HLBN:Check (HLBN:PromptIs 'landing before)
      "HLBH 未进入预期的文字落点提示，停止自动放置并撤销本批次。")
    (setq before (getvar "LASTPROMPT"))
    (HLBN:Log "INPUT_POINT" (list 'landing (HLBN:Get 'handle row) landing))
    (command landing)
    (HLBN:Log "INPUT_RETURN" (list 'landing (HLBN:CommandState)))
    (setq created (HLBN:After tail))
    (HLBN:Log "CREATED" (mapcar '(lambda (e) (list (cdr (assoc 5 (entget e)))
      (cdr (assoc 0 (entget e))))) created))
    (HLBN:Check created "HLBH 未生成标注，停止处理下一条导线。")
    (HLBN:Check (HLBN:PromptIs 'wire before)
      "HLBH 生成标注后未返回选线流程，本批次未确认完成。")
    (setq entity (HLBN:SetLabel created (HLBN:Get 'label row)))
    (setq verified (cons (list entity (HLBN:Get 'label row) (cdr (assoc 0 (entget entity)))) verified))
    (HLBN:Log "ROW_COMPLETE" (list (HLBN:Get 'handle row) (HLBN:Get 'label row)))
    (HLBN:Check (> (logand 8 (getvar "UNDOCTL")) 0)
      "天正命令改变了当前撤销分组，请保留日志并检查撤销状态。"))
  (HLBN:Check (HLBN:PromptIs 'wire before) "HLBH 最后一条标注后的提示异常，本批次未确认完成。")
  (command "")
  (HLBN:Log "NATIVE_EXIT" (HLBN:CommandState))
  (HLBN:Check (not (HLBN:CommandBusy)) "HLBH 没有正常退出，请保留实际命令行提示。")
  ;; Re-read all rows after HLBH exits; native auto-increment must not change them.
  (foreach row verified
    (HLBN:Check (and (equal (cadr row) (HLBN:Get 'text (HLBN:TextInfo (car row))))
                    (equal (caddr row) (cdr (assoc 0 (entget (car row))))))
      "HLBH 退出后编号或原生对象类型发生变化，本批次将撤销。"))
  (reverse verified))

(defun HLBN:RestoreVars (values / item)
  (foreach item values (vl-catch-all-apply 'setvar (list (car item) (cdr item)))))
(defun HLBN:SameDocument (context)
  (equal (HLBN:Get 'document context) (vla-get-ActiveDocument (vlax-get-acad-object))))
(defun HLBN:DrawingState (/ entity result)
  ;; Only used for interrupted recovery: refuse to undo later drawing work.
  (setq entity (entnext))
  (while entity
    (setq result (cons (entget entity '("*")) result) entity (entnext entity)))
  (reverse result))
(defun HLBN:Rollback (context in-error / tail snapshot changed result)
  (setq tail (HLBN:Get 'tail context) snapshot (HLBN:Get 'snapshot context))
  ;; command-s UNDO must never run over an active native command.
  (if (and (HLBN:SameDocument context) (HLBN:NativeActive) (not in-error)) (HLBN:StopNative))
  (cond
    ((not (HLBN:SameDocument context)) nil)
    ((HLBN:CommandBusy) nil)
    ((not (HLBN:Get 'group context))
      (and (not (HLBN:After tail)) (HLBN:SameSources snapshot)))
    ((and (assoc 'failed-state context)
          (not (equal (HLBN:Get 'failed-state context) (HLBN:DrawingState)))
          (or (HLBN:After tail) (not (HLBN:SameSources snapshot))))
      (princ "\n失败后图纸已有后续改动，未自动撤销这些改动；请在原图手动撤销本批次后再运行 HLPLBHRECOVER。") nil)
    ((= 0 (logand 8 (getvar "UNDOCTL")))
      (and (not (HLBN:After tail)) (HLBN:SameSources snapshot)))
    (T
      (setq changed (or (HLBN:After tail) (not (HLBN:SameSources snapshot))))
      (setq result (vl-catch-all-apply 'command-s '("_.UNDO" "_End")))
      (if (not (vl-catch-all-error-p result))
        (progn
          ;; An empty batch must not undo the user's preceding drawing command.
          (if changed (setq result (vl-catch-all-apply 'command-s '("_.U"))))
          (if (and (not (vl-catch-all-error-p result)) (not (HLBN:After tail))
                   (HLBN:SameSources snapshot)) T))))))
(defun HLBN:Cleanup (in-error / ok same)
  (if *HLBN:Pending*
    (progn
      (setq ok (vl-catch-all-apply 'HLBN:Rollback (list *HLBN:Pending* in-error)))
      (if (vl-catch-all-error-p ok)
        (progn
          (HLBN:Log "ROLLBACK_ERROR" (list (vl-catch-all-error-message ok) (HLBN:CommandState)))
          (setq ok nil)))
      (setq same (vl-catch-all-apply 'HLBN:SameDocument (list *HLBN:Pending*)))
      (if (and same (not (vl-catch-all-error-p same)))
        (HLBN:RestoreVars (HLBN:Get 'vars *HLBN:Pending*)))
      (HLBN:Log "ROLLBACK" (list ok hlbn-failure (HLBN:CommandState)))
      (if ok (setq *HLBN:Pending* nil)
        (progn
          (if (and same (not (vl-catch-all-error-p same))
                   (not (assoc 'failed-state *HLBN:Pending*)))
            (setq *HLBN:Pending* (cons (cons 'failed-state (HLBN:DrawingState)) *HLBN:Pending*)))
          (princ "\n自动撤销未确认完成。请先 Esc 退出当前命令，期间不要继续绘图，在原图运行 HLPLBHRECOVER；日志已保留。")
          (if (and same (not (vl-catch-all-error-p same)) (= 0 (logand 8 (getvar "UNDOCTL"))))
            (princ "\n当前撤销分组已改变，请先在原图手动撤销本批次，再运行 HLPLBHRECOVER 核对。"))))
      ok)))
(defun c:HLPLBHRECOVER (/ hlbn-failure)
  (if *HLBN:Pending*
    ;; Recovery must not cancel a different command started after our failure.
    (if (HLBN:Cleanup T) (princ "\n本工具未完成的批次已撤销。"))
    (princ "\n本工具没有待恢复的批次。"))
  (princ))

(defun HLBN:Execute (plan / vars item context result hlbn-failure)
  (HLBN:Check (and (> (logand 1 (getvar "UNDOCTL")) 0)
                  (= 0 (logand 10 (getvar "UNDOCTL"))))
    "当前撤销被禁用、仅允许一步撤销或已有撤销分组，请恢复普通撤销状态后再运行。")
  (foreach item '("CMDECHO" "OSMODE" "ORTHOMODE" "SNAPMODE" "DYNMODE")
    (setq vars (cons (cons item (getvar item)) vars)))
  (setq context (list (cons 'tail (HLBN:Tail)) (cons 'snapshot (HLBN:Snapshot plan))
    (cons 'document (vla-get-ActiveDocument (vlax-get-acad-object))) (cons 'vars vars)))
  (setq *HLBN:Pending* context)
  (HLBN:Log "BEGIN" (list "2026.10.11.3" (HLBN:CommandState) (length plan) (HLBN:DefaultOffset)))
  (setvar "CMDECHO" 1)
  (foreach item '("OSMODE" "ORTHOMODE" "SNAPMODE" "DYNMODE") (setvar item 0))
  (command-s "_.UNDO" "_Begin")
  (setq *HLBN:Pending* (cons (cons 'group T) context))
  (setq result (vl-catch-all-apply 'HLBN:NativeRun (list plan)))
  ;; EXIT/QUIT may leave vl-catch-all-apply with NIL rather than an error object.
  ;; A successful return must contain every verified row and an idle CAD state.
  (if (or (vl-catch-all-error-p result) (not result) (not (listp result))
          (/= (length result) (length plan)) hlbn-failure (HLBN:CommandBusy))
    (progn
      (if (not hlbn-failure)
        (setq hlbn-failure (if (vl-catch-all-error-p result) (vl-catch-all-error-message result)
          "HLBH 未返回完整的已核对标注，不能确认本批次完成。")))
      (HLBN:Log "FAILED" (list hlbn-failure (HLBN:CommandState)))
      (princ (strcat "\n批量编号未完成：" hlbn-failure))
      (if (HLBN:Cleanup nil) (princ "\n已撤销本批次，原导线恢复。")) nil)
    (progn
      (command-s "_.UNDO" "_End")
      (setq *HLBN:Pending* nil)
      (HLBN:RestoreVars vars)
      (HLBN:Log "COMPLETE" (mapcar 'cadr result))
      result)))
(defun c:HLPLBH (/ *error* start parts selection rows skipped plan result hlbn-failure)
  (defun *error* (message)
    (if *HLBN:Pending* (HLBN:Cleanup T))
    (princ (strcat "\n批量编号已停止：" (if hlbn-failure hlbn-failure message)))
    (princ (strcat "\n日志：" (HLBN:Log "ERROR" (list hlbn-failure message))))
    (princ))
  (cond
    (*HLBN:Pending* (princ "\n请先在原图运行 HLPLBHRECOVER，恢复上次未完成的批次。"))
    ((HLBN:CommandBusy) (princ "\n请先结束当前绘图命令，再运行 HLPLBH。"))
    (T
      (setq start (getstring T (strcat "\n起始回路编号 <"
        (if *HLBN:LastStart* *HLBN:LastStart* "ZE1") ">: ")))
      (if (= start "") (setq start (if *HLBN:LastStart* *HLBN:LastStart* "ZE1")))
      (setq parts (HLBN:NumberParts start))
      (HLBN:Check parts "编号必须以数字结尾，例如 ZE1、ZE009 或 4ALE(JZ)-ZE1。")
      (princ "\n框选需要编号的独立出线段，排除母线和已有引线；回车结束选择。")
      (setq selection (ssget "_:L"))
      (if selection
        (progn
          (setq rows (HLBN:Rows selection) skipped (cadr rows) rows (car rows))
          (if (> skipped 0) (princ (strcat "\n已跳过 " (itoa skipped) " 个非开放导线或不支持的对象。")))
          (HLBN:Check rows "没有可标注的开放导线，请重新框选独立出线。")
          (setq plan (HLBN:Plan rows parts (HLBN:DefaultOffset)))
          (HLBN:Log "PLAN" plan)
          (setq result (HLBN:Execute plan))
          (if result
            (progn
              (setq *HLBN:LastStart* (HLBN:NumberAt parts 0))
              (princ (strcat "\n已通过 HLBH 生成并核对 " (itoa (length result)) " 组标注："
                (cadar result) " 至 " (cadr (car (last result))) "。单次 UNDO 可撤销本批次。")))))
        (princ "\n没有选择导线，图纸未修改。"))))
  (princ (strcat "\n日志：" (strcat (getvar "TEMPPREFIX") "HLPLBH-debug.log")))
  (princ))
(defun c:HLPLBHSET (/ offset x y)
  (setq offset (HLBN:DefaultOffset))
  (setq x (getreal (strcat "\n水平偏移，右为正、左为负 <" (rtos (car offset) 2 2) ">：")))
  (setq y (getreal (strcat "\n竖向偏移，上为正、下为负 <" (rtos (cadr offset) 2 2) ">：")))
  (if (not x) (setq x (car offset)))
  (if (not y) (setq y (cadr offset)))
  (if (and (= x 0.0) (= y 0.0))
    (princ "\n两个偏移不能同时为 0，已保留原设置。")
    (setq *HLBN:Offset* (list x y 0.0)))
  (setq offset (HLBN:DefaultOffset))
  (princ (strcat "\n每根导线的文字点偏移：X=" (rtos (car offset) 2 2)
    "，Y=" (rtos (cadr offset) 2 2) "。"))
  (princ))

(princ "\n批量回路编号已加载（2026.10.11.3）：HLPLBH；偏移设置：HLPLBHSET；异常恢复：HLPLBHRECOVER。")
(princ)

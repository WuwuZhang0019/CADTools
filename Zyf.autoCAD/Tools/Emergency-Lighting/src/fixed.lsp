;; Date: 2026-10-09. Fixed dynamic templates; legacy template schema is retained.
(defun EL:FixedTemplate (template)
  (and (EL:TemplateValid template)
    (equal (EL:Get 'name (EL:Get 'panel template)) "ZYF_Tool_应急照明配电箱图块")
    (equal (EL:Get 'name (EL:Get 'circuit template)) "ZYF_Tool_应急照明配电回路图块")))
(defun EL:FixedText ()
  ;; Date: 2026-10-09. User-supplied TEXT appearance; never sample again.
  (if (tblsearch "STYLE" "_TEL_DIM")
    '((offset 10983.0 -450.0 0.0) (type . "TEXT") (style . "_TEL_DIM")
      (height . 350.0) (width . 0.0) (align . 1) (rotation . 0.0)
      (factor . 0.7) (oblique . 0.0) (layer . "TEL_TEXT"))
    (progn (princ "\n缺少文字样式 _TEL_DIM，请将含此样式的文字拷入本图后重试。") nil)))
(defun EL:FindFixedBlock (name / ss i e found)
  (setq ss (ssget "_X" '((0 . "INSERT"))) i 0)
  (if ss
    (while (and (< i (sslength ss)) (not found))
      (setq e (ssname ss i) i (1+ i))
      (if (equal (strcase (EL:EffectiveName e)) (strcase name)) (setq found e)))) found)
(defun EL:WithFixedBlock (name function args / e object outcome cleanup)
  ;; Existing references are read only. A definition-only probe is always deleted.
  (cond
    ((setq e (EL:FindFixedBlock name)) (apply function (cons e args)))
    ((not (tblsearch "BLOCK" name))
      (princ (strcat "\n未找到系统图块 " name "，请将该图块拷入当前图纸后重试。")) nil)
    (T
      (EL:FreshBoundary)
      (setq object (vl-catch-all-apply 'vla-InsertBlock
        (list (vla-get-ModelSpace (vla-get-ActiveDocument (vlax-get-acad-object)))
          (vlax-3d-point '(0.0 0.0 0.0)) name 1.0 1.0 1.0 0.0)))
      (if (vl-catch-all-error-p object)
        (progn (princ "\n无法检查已有图块定义，请检查当前图层或将该图块拷入模型空间后重试。") nil)
        (progn
          (setq outcome (vl-catch-all-apply function (cons (vlax-vla-object->ename object) args))
            cleanup (vl-catch-all-apply 'vla-Delete (list object)))
          ;; Date: 2026-10-11. Do not retain samples created by the probe or
          ;; its cleanup reactors while the temporary block still existed.
          (EL:FreshBoundary)
          (EL:Require (not (vl-catch-all-error-p cleanup)) "临时图块清理失败，请撤销本次模板检查后重试。")
          (if (vl-catch-all-error-p outcome)
            (progn (princ "\n图块检查未完成，临时对象已清理。") nil)
            (if (and outcome (listp outcome)) (EL:Put 'source-handle nil outcome) outcome)))))))
(defun EL:FixedDefinitionValid (e definition / obj property)
  (setq obj (vlax-ename->vla-object e) property (EL:DynamicProperty obj (EL:Get 'property definition)))
  (and property (= (vla-get-ReadOnly property) :vlax-false)
    (vl-every '(lambda (state) (member (EL:Get 'value state) (EL:AllowedValues property)))
      (EL:Get 'states definition))))
(defun EL:TemplateValueText (value)
  (if (equal (type value) 'STR) value (rtos value 2 6)))
(defun EL:TemplateValuesValid (values)
  (and (listp values) (>= (length (EL:Unique values)) 3)
    (vl-every '(lambda (value) (or (and (equal (type value) 'STR) (/= value "")) (EL:Number value))) values)))
(defun EL:TemplateKey (value / i ch textdata)
  (if (equal (type value) 'STR)
    (progn
      (setq i 1 textdata "")
      (while (<= i (strlen value))
        (setq ch (substr value i 1) i (1+ i))
        (if (not (member ch '(" " "\t" "\r" "\n"))) (setq textdata (strcat textdata ch))))
      (strcase textdata))))
(defun EL:TemplateMatches (value option kind)
  (or (equal (EL:TemplateKey value) (EL:TemplateKey (EL:OptionLabel option)))
    ;; Only the fixed circuit template calls this with this business kind.
    (and (equal kind "回路类型") (equal option 'ground) (equal value "埋地"))))
(defun EL:TemplateMatchingValues (values option kind)
  (EL:Unique (vl-remove-if-not '(lambda (v) (EL:TemplateMatches v option kind)) values)))
(defun EL:TemplateChoose (title labels / i label index done)
  (princ (strcat "\n" title)) (setq i 0)
  (foreach label labels (setq i (1+ i)) (princ (strcat "\n  " (itoa i) ". " label)))
  (while (not done)
    (setq index (getint (if (= (length labels) 1)
      "\n仅剩上述状态，但含义仍需核对。输入 1 确认对应（回车取消本次模板设置）："
      (strcat "\n请输入选项前的数字 1-" (itoa (length labels)) "（回车取消本次模板设置）："))))
    (cond
      ((not index) (princ "\n已取消本次模板设置，原模板保持不变。") (setq done T))
      ((and (> index 0) (<= index (length labels))) (setq done T))
      (T (princ "\n数字超出范围，请按上面的编号重新选择。")))) index)
(defun EL:TemplatePropertyText (prop / textdata value)
  (setq textdata (strcat (vla-get-PropertyName prop) "（可选状态："))
  (foreach value (EL:AllowedValues prop) (setq textdata (strcat textdata (EL:TemplateValueText value) "；")))
  (strcat textdata "）"))
(defun EL:TemplateProperty (props options kind / eligible exact prop values choices index)
  (foreach prop props
    (if (and (= (vla-get-ReadOnly prop) :vlax-false)
        (EL:TemplateValuesValid (setq values (EL:AllowedValues prop))))
      (progn
        (setq eligible (cons prop eligible))
        (if (vl-every '(lambda (o) (= (length (EL:TemplateMatchingValues values o kind)) 1)) options)
          (setq exact (cons prop exact))))))
  (setq choices (reverse (if exact exact eligible)))
  (cond
    ((not choices) (princ (strcat "\n这个图块没有找到可修改且至少有三种状态的选项，无法设置" kind "。")) nil)
    ((= (length choices) 1) (car choices))
    (T (setq index (EL:TemplateChoose (strcat "这个图块有多个选项。哪一项控制" kind "？")
        (mapcar 'EL:TemplatePropertyText choices)))
      (if index (nth (1- index) choices)))))
(defun EL:TemplateStates (values options annotation kind / remaining reserved used option other label available matches index value states contour cancelled)
  ;; Reserve exact names before manual choices so they cannot be assigned twice.
  (setq remaining options contour (EL:BoundsSegments '((-100.0 -100.0 0.0) (100.0 100.0 0.0))))
  (while (and remaining (not cancelled))
    (setq option (car remaining) remaining (cdr remaining) label (EL:OptionLabel option) value nil)
    (setq matches (EL:TemplateMatchingValues values option kind))
    (if (= (length matches) 1) (setq value (car matches))
      (progn
        (setq reserved nil)
        (foreach other options
          (if (not (equal other option))
            (setq reserved (append reserved (EL:TemplateMatchingValues values other kind)))))
        (setq available (EL:Unique (vl-remove-if '(lambda (v) (or (member v used) (member v reserved))) values)))
        (setq index (EL:TemplateChoose (strcat kind "“" label "”对应下面哪种状态？已分配的状态不再列出。")
          (mapcar 'EL:TemplateValueText available)))
        (if index (setq value (nth (1- index) available)) (setq cancelled T))))
    (if (not cancelled)
      (progn
        (setq used (cons value used))
        (princ (strcat "\n已对应：" kind " " label " = 图块状态“" (EL:TemplateValueText value) "”"))
        ;; Preview bounds only; the source block is never modified during capture.
        (setq states (cons (list (cons 'option option) (cons 'value value)
          (cons 'connection (if annotation '(0.0 0.0 0.0) '(6427.0 -5500.0 0.0)))
          (cons 'contour contour) (cons 'text annotation)) states)))))
  (if (not cancelled) (reverse states)))
(defun EL:FixedCapture (name options annotation)
  (EL:WithFixedBlock name 'EL:FixedCaptureEntity (list name options annotation)))
(defun EL:FixedCaptureEntity (e name options annotation / obj prop states kind)
  (setq kind (if annotation "回路类型" "箱体容量") obj (vlax-ename->vla-object e))
  (if (/= (vla-get-IsDynamicBlock obj) :vlax-true)
    (progn (princ (strcat "\n图块 " name " 不是动态块，请拷入正确图块后重试。")) nil)
    (if (setq prop (EL:TemplateProperty (vlax-invoke obj 'GetDynamicBlockProperties) options kind))
      (progn
        (princ (strcat "\n自动找到 " name "，使用“" (vla-get-PropertyName prop) "”设置" kind "。"))
        (if (setq states (EL:TemplateStates (EL:AllowedValues prop) options annotation kind))
          (list (cons 'name name) (cons 'property (vla-get-PropertyName prop))
            (cons 'source-handle (cdr (assoc 5 (entget e))))
            (cons 'definition (EL:Signature (EL:DefinitionData name nil))) (cons 'states states)))))))
(defun EL:FixedOutputCount (count)
  ;; CCKK2 supports eight physical rows. Never drop actual circuits.
  (if (and (<= 1 count) (<= count 8)) (min 8 (+ count 2)) count))
(defun EL:FixedOutputs (circuits / out c index used text reserve)
  (setq index 0)
  (foreach c circuits
    (setq index (1+ index) text (EL:CircuitNumberText c index) used (cons (EL:NumberKey text) used))
    (setq out (cons (list (cons 'circuit-id (EL:Get 'id c)) (cons 'label (EL:Get 'id c))
      (cons 'circuit-number text)
      (cons 'mode (if (EL:Get 'is-ground c) 'ground 'normal))) out)))
  (setq out (reverse out) reserve 0)
  (repeat (- (EL:FixedOutputCount (length circuits)) (length circuits))
    (setq index (1+ index) reserve (1+ reserve) text (EL:DefaultCircuitNumber index used)
      used (cons (EL:NumberKey text) used) out (append out (list (list
      (cons 'label (strcat "reserve-" (itoa reserve))) (cons 'circuit-number text) '(mode . reserve)))))) out)
(defun EL:FixedPlan (result template capacity origin rotation scale / plan rows row i c spec position layout slot outputs)
  (if (and (EL:CircuitNumbersReady result) (EL:FixedTemplate template)
      (setq layout (EL:CCKK2Rows (length (EL:Get 'circuits result)))))
    (progn
      (setq outputs (EL:FixedOutputs (EL:Get 'circuits result))
        plan (EL:BuildGenerationPlan result template capacity outputs origin rotation scale) i 0)
      (foreach row (EL:Get 'rows plan)
        (setq c (EL:By 'id (EL:Get 'circuit-id row) (EL:Get 'circuits result))
              slot (nth i layout)
              position (EL:LocalPoint (list (car slot) (cadr slot) 0.0) origin rotation scale)
              spec (EL:Put 'align 1 (EL:Put 'offset '(10983.0 -450.0 0.0) (EL:Get 'annotation row)))
              row (EL:Put 'position position (EL:Put 'annotation spec row))
              row (EL:Put 'text-position (if c (EL:LocalPoint '(10983.0 -450.0 0.0) position rotation scale)) row)
              row (EL:Put 'text (if c (strcat (itoa (EL:Get 'watts c)) "W")) row)
              row (EL:Put 'circuit-number (EL:Get 'circuit-number (nth i outputs)) row)
              row (EL:Put 'circuit-uid (if c (EL:Get 'circuit-uid c) (EL:Get 'label row)) row)
              rows (cons row rows) i (1+ i)))
      (if plan (EL:Put 'panel-number (EL:PanelNumber result) (EL:Put 'cckk-layout T (EL:Put 'rows (reverse rows) plan)))))))
(defun EL:CaptureFixedTemplate (cfg / annotation panel circuit template)
  (if (EL:EnsureSystemBlocks
      '("ZYF_Tool_应急照明配电箱图块" "ZYF_Tool_应急照明配电回路图块") '("_TEL_DIM" "ICDA-STYLE1"))
    (progn
      (EL:FreshBoundary)
      (if (not (tblsearch "STYLE" "ICDA-STYLE1"))
        (princ "\n缺少箱号文字样式 ICDA-STYLE1，请将使用该样式的文字复制到本图。"))
      (if (and (tblsearch "STYLE" "ICDA-STYLE1") (setq annotation (EL:FixedText)))
        (progn
          (princ "\n自动读取本图系统图块；文字使用 _TEL_DIM、高350、宽度因子0.7。单位固定 mm。")
          (if annotation (setq panel (EL:FixedCapture "ZYF_Tool_应急照明配电箱图块" '(cap300 cap600 cap1000) nil)))
          (if panel (setq circuit (EL:FixedCapture "ZYF_Tool_应急照明配电回路图块" '(normal ground reserve) annotation)))
          (setq template (list (cons 'panel panel) (cons 'circuit circuit) '(step 0.0 -1200.0 0.0)
            '(actual-format . "{回路功率W}W") '(reserve-format . "预留") '(layer . "SYS_系统标注_E")))
          (cond
            ((not (and panel circuit)) (princ "\n本次模板设置未完成，原模板保持不变。") nil)
            ((not (EL:TemplateRuntimeValid template cfg))
              (princ "\n模板校验未通过，未保存。请核对样本状态、文字样式及输出图层是否可用。") nil)
            (T template)))))))
(defun EL:TemplateReady (template cfg / checked)
  (if (and (EL:FixedTemplate template)
      (equal (EL:Get 'layer template) "SYS_系统标注_E")
      (tblsearch "STYLE" "ICDA-STYLE1")
      (vl-every '(lambda (state) (equal (EL:Get 'text state) (EL:FixedText)))
        (EL:Get 'states (EL:Get 'circuit template))))
    (progn (setq checked (vl-catch-all-apply 'EL:TemplateRuntimeValid (list template cfg)))
      (and (not (vl-catch-all-error-p checked)) checked))))
(defun c:ELTEMPLATE (/ *error* cfg template)
  (defun *error* (msg) (EL:ClearPickHighlights) (if msg (princ msg)) (princ))
  (if (and (setq cfg (EL:LoadConfig)) (setq template (EL:CaptureFixedTemplate cfg)))
    (if (EL:SaveConfig (EL:Put 'template template cfg))
          (princ "\n模板设置已保存：箱体容量和回路类型已对应。生成时请核对实际图形。")
      (princ "\n模板配置写入失败，未完成保存；请检查配置目录是否可写。")))
  (EL:ClearPickHighlights) (princ))

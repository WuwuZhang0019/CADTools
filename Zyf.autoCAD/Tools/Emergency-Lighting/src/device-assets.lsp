;; Date: 2026-10-12. Explicit ADO arguments; immutable assets and owned previews.
(defun EL:DLBytesWork (stream path count)
  (vlax-put-property stream 'Type 1) (vlax-invoke-method stream 'Open nil 0 -1 "" "")
  (vlax-invoke-method stream 'LoadFromFile path)
  (vlax-safearray->list (vlax-variant-value (vlax-invoke-method stream 'Read count))))
(defun EL:DLBytes (path count / stream result)
  (setq stream (vlax-create-object "ADODB.Stream") result (vl-catch-all-apply 'EL:DLBytesWork (list stream path count)))
  (vl-catch-all-apply 'vlax-invoke-method (list stream 'Close)) (vlax-release-object stream)
  (if (not (vl-catch-all-error-p result)) result))
(defun EL:DLDWGValid (path / bytes)
  (setq bytes (if (findfile path) (EL:DLBytes path 6)))
  (and (= (length bytes) 6) (equal (list (car bytes) (cadr bytes) (caddr bytes) (cadddr bytes)) '(65 67 49 48))
    (vl-every '(lambda (n) (and (>= n 48) (<= n 57))) (list (nth 4 bytes) (nth 5 bytes)))))
(defun EL:DLSLDWord (bytes index swapped)
  (if swapped (+ (* 256 (nth index bytes)) (nth (1+ index) bytes))
    (+ (nth index bytes) (* 256 (nth (1+ index) bytes)))))
(defun EL:DLSLDSize (path / bytes prefix index swapped)
  (setq bytes (if (findfile path) (EL:DLBytes path 31)) index 0)
  (repeat 17 (setq prefix (cons (nth index bytes) prefix) index (1+ index)))
  (if (and (= (length bytes) 31) (equal (reverse prefix) '(65 117 116 111 67 65 68 32 83 108 105 100 101 13 10 26 0))
      ;; The documented hex dump uses 0x56 = 86, not decimal 56 (0x38).
      (= (nth 17 bytes) 86) (= (nth 18 bytes) 2)
      (or (equal (list (nth 29 bytes) (nth 30 bytes)) '(52 18))
          (equal (list (nth 29 bytes) (nth 30 bytes)) '(18 52))))
    (progn (setq swapped (= (nth 29 bytes) 18))
      (list (1+ (EL:DLSLDWord bytes 19 swapped)) (1+ (EL:DLSLDWord bytes 21 swapped))))))
(defun EL:DLChecksum (path / size bytes hash byte)
  (setq size (if (findfile path) (vl-file-size path)))
  (if (and size (> size 0) (<= size 8388608) (setq bytes (EL:DLBytes path -1)) (= size (length bytes)))
    (progn (setq hash 0)
      (foreach byte bytes (setq hash (fix (rem (+ (* hash 131.0) byte) 2147483647.0))))
      (strcat "sld-" (itoa hash) "-" (itoa size)))))
(defun EL:DLFilesEqualWork (a b left right / size good x y)
  (foreach x (list left right) (vlax-put-property x 'Type 1) (vlax-invoke-method x 'Open nil 0 -1 "" ""))
  (vlax-invoke-method left 'LoadFromFile a) (vlax-invoke-method right 'LoadFromFile b)
  (setq size (vlax-get-property left 'Size) good (and (> size 0) (<= size 67108864) (= size (vlax-get-property right 'Size))))
  (while (and good (< (vlax-get-property left 'Position) size))
    (setq x (vlax-safearray->list (vlax-variant-value (vlax-invoke-method left 'Read 65536)))
      y (vlax-safearray->list (vlax-variant-value (vlax-invoke-method right 'Read 65536))) good (equal x y))) good)
(defun EL:DLFilesEqual (a b / left right result stream)
  (setq left (vlax-create-object "ADODB.Stream") right (vlax-create-object "ADODB.Stream")
    result (vl-catch-all-apply 'EL:DLFilesEqualWork (list a b left right)))
  (foreach stream (list left right)
    (vl-catch-all-apply 'vlax-invoke-method (list stream 'Close)) (vlax-release-object stream))
  (and (not (vl-catch-all-error-p result)) result))
(defun EL:DLFolderClaim (path / fso result)
  (setq fso (vlax-create-object "Scripting.FileSystemObject") result (vl-catch-all-apply 'vlax-invoke-method (list fso 'CreateFolder path)))
  (if (not (vl-catch-all-error-p result)) (vlax-release-object result)) (vlax-release-object fso)
  (not (vl-catch-all-error-p result)))
(defun EL:DLAssetInstall (snapshot entry dwg slide / root revision folder next size prefix)
  (setq root (EL:Get 'root snapshot) revision (1+ (EL:Get 'asset-revision entry)) size (EL:DLSLDSize slide))
  (EL:Require (and (EL:DLToken (EL:Get 'device-id entry)) (EL:DLDWGValid dwg) size) "图形或图例文件无效，未发布。")
  (EL:Require (EL:DLMkdir (strcat root "assets/" (EL:Get 'device-id entry))) "图形资产目录不可写。")
  (setq folder (strcat root "assets/" (EL:Get 'device-id entry) "/" (itoa revision)))
  (while (vl-file-directory-p folder) (setq revision (1+ revision) folder (strcat root "assets/" (EL:Get 'device-id entry) "/" (itoa revision))))
  (EL:Require (EL:DLFolderClaim folder) "资产版本被其他窗口占用，请重试。") (setq folder (strcat folder "/"))
  (EL:Require (and (vl-file-copy dwg (strcat folder "block.dwg")) (EL:DLFilesEqual dwg (strcat folder "block.dwg"))
    (vl-file-copy slide (strcat folder "legend.sld")) (EL:DLFilesEqual slide (strcat folder "legend.sld")))
    "图形复制回读失败，设备库未发布；原版本保留。")
  (setq next (EL:Put 'asset-revision revision entry) prefix (EL:DLAssetPrefix next)
    next (EL:Put 'block-file (strcat prefix "block.dwg") (EL:Put 'legend-file (strcat prefix "legend.sld")
      (EL:Put 'legend-checksum (EL:DLChecksum (strcat folder "legend.sld")) (EL:Put 'legend-size size next)))))
  (EL:Require (EL:Get 'legend-checksum next) "图例校验失败，设备库未发布。") next)
(defun EL:DLLegend (entry snapshot / path size checksum)
  ;; A saved draft can already have a valid graphic before watts/ground are complete.
  (if (and entry (EL:DLEntryAssets entry)) (progn (setq path (strcat (EL:Get 'root snapshot) (EL:Get 'legend-file entry)))
    (if (and (setq size (EL:DLSLDSize path)) (equal size (EL:Get 'legend-size entry))
        (setq checksum (EL:DLChecksum path)) (equal checksum (EL:Get 'legend-checksum entry)))
      (progn (EL:PerfCount "device-legend-loads" 1) (list path size))))))
(defun EL:DLExportWork (entity path doc / array)
  (setq *EL:DLExportSet* (vla-Add (vla-get-SelectionSets doc) (EL:DLOperationID)) array (vlax-make-safearray vlax-vbObject '(0 . 0)))
  (vlax-safearray-fill array (list (vlax-ename->vla-object entity)))
  (vla-AddItems *EL:DLExportSet* array) (vla-WBlock doc path *EL:DLExportSet*) T)
(defun EL:DLExport (entity path / doc result *EL:DLExportSet*)
  (setq doc (vla-get-ActiveDocument (vlax-get-acad-object)) result (vl-catch-all-apply 'EL:DLExportWork (list entity path doc)))
  (if *EL:DLExportSet* (vl-catch-all-apply 'vla-Delete (list *EL:DLExportSet*)))
  (and (not (vl-catch-all-error-p result)) result (EL:DLDWGValid path)))
(defun EL:DLPickBlock (/ picked entity data definition)
  (setq picked (entsel "\n拾取设备图块（Esc 保留编辑内容）：") entity (car picked))
  (if entity (progn (setq data (entget entity) definition (tblsearch "BLOCK" (EL:EffectiveName entity)))
    (if (and (equal (cdr (assoc 0 data)) "INSERT") definition (= (logand (cdr (assoc 70 definition)) 12) 0)) entity
      (progn (alert "请选择本图中的设备 INSERT；外部参照不能登记为设备。") nil)))))
;; Date: 2026-10-12. Independent multi-pick; one representative per exact effective name.
(defun EL:DLPickDevices (/ selected index entity data definition name names out preset)
  (setq preset (EL:PresetLoad))
  (princ (strcat "\n选择要入库的设备图块，可框选多种；设备图层：" (EL:DLAliasText (EL:Get 'device-layers preset))
    "。Enter 完成选择，Esc 返回设备库。"))
  (setq selected (EL:PerfInput 'ssget (list '((0 . "INSERT") (410 . "Model")))) index 0)
  (while (and selected (< index (sslength selected)))
    (setq entity (ssname selected index) data (entget entity) name (EL:EffectiveName entity)
      definition (tblsearch "BLOCK" name))
    (if (and (equal (cdr (assoc 0 data)) "INSERT") (equal (cdr (assoc 410 data)) "Model")
        definition (= (logand (cdr (assoc 70 definition)) 12) 0) (not (EL:ManagedEntity entity))
        (EL:PresetMember (cdr (assoc 8 data)) (EL:Get 'device-layers preset))
        (not (and (EL:PresetMember (cdr (assoc 8 data)) (EL:Get 'panel-layers preset))
          (EL:PresetMember name (EL:Get 'panel-names preset))))
        (not (member (EL:DLNameKey name) names)))
      (setq names (cons (EL:DLNameKey name) names) out (append out (list entity))))
    (setq index (1+ index))) out)
(defun EL:DLCaptureScript (job / slide marker source fullname token)
  (setq slide (vl-prin1-to-string (EL:Get 'slide job)) marker (vl-prin1-to-string (EL:Get 'marker job))
    source (vl-prin1-to-string (EL:Get 'source-name job)) fullname (vl-prin1-to-string (cond ((EL:Get 'source-fullname job)) (T "")))
    token (vl-prin1-to-string (EL:Get 'token job)))
  (strcat "(progn (vl-load-com) (setq el_dl_filedia (getvar \"FILEDIA\") el_dl_cmdecho (getvar \"CMDECHO\")) "
    "(setq el_dl_outcome (vl-catch-all-apply '(lambda () "
    "(setvar \"FILEDIA\" 0) (setvar \"CMDECHO\" 0) (setvar \"TILEMODE\" 1) (setvar \"UCSFOLLOW\" 0) "
    ;; WBlock retains layer state. Normalize only this owned temporary drawing.
    "(vlax-for el_dl_layer (vla-get-Layers (vla-get-ActiveDocument (vlax-get-acad-object))) "
    "(vla-put-Lock el_dl_layer :vlax-false) (vla-put-Freeze el_dl_layer :vlax-false) (vla-put-LayerOn el_dl_layer :vlax-true)) "
    "(command-s \"_.UCS\" \"_World\") (command-s \"_.PLAN\" \"_World\") "
    "(vla-ZoomExtents (vlax-get-acad-object)) (command-s \"_.ZOOM\" \"0.8x\") "
    "(vla-Regen (vla-get-ActiveDocument (vlax-get-acad-object)) 1) (command-s \"_.MSLIDE\" " slide ") T) nil)) "
    "(setvar \"FILEDIA\" el_dl_filedia) (setvar \"CMDECHO\" el_dl_cmdecho) "
    "(setq el_dl_file (open " marker " \"w\")) (if el_dl_file (progn "
    "(write-line (if (vl-catch-all-error-p el_dl_outcome) \"FAILED\" \"DONE\") el_dl_file) (close el_dl_file))) "
    "(setq el_dl_source nil) (vlax-for el_dl_document (vla-get-Documents (vlax-get-acad-object)) "
    "(if (and (equal (vla-get-Name el_dl_document) " source ") "
    "(equal (strcase (vla-get-FullName el_dl_document)) (strcase " fullname "))) (setq el_dl_source el_dl_document))) "
    "(if el_dl_source (vla-SendCommand el_dl_source "
    (vl-prin1-to-string (strcat "(EL:DLCaptureResume " token ")\n")) ")) (princ))\n"))
(defun EL:DLCaptureQueue (job / documents temporary)
  (setq documents (vla-get-Documents (vlax-get-acad-object)) temporary (vla-Open documents (EL:Get 'dwg job) :vlax-true))
  (setq *EL:DLCaptureJob* (EL:Put 'temporary temporary *EL:DLCaptureJob*))
  (vla-SendCommand temporary (EL:DLCaptureScript job)) T)
(defun EL:DLCapturePublishJob (snapshot entry token folder / source job result)
  (setq source (vla-get-ActiveDocument (vlax-get-acad-object))
    job (list (cons 'token token) (cons 'snapshot snapshot) (cons 'entry entry) (cons 'dwg (strcat folder "/block.dwg"))
      (cons 'slide (strcat folder "/legend.sld")) (cons 'marker (strcat folder "/complete.txt"))
      (cons 'source-name (vla-get-Name source)) (cons 'source-fullname (vla-get-FullName source)) (cons 'source source)) *EL:DLCaptureJob* job)
  (setq result (vl-catch-all-apply 'EL:DLCaptureQueue (list job)))
  (if (vl-catch-all-error-p result) (progn (setq *EL:DLCaptureJob* (EL:Put 'failed T *EL:DLCaptureJob*))
    (if (EL:DLCaptureClose *EL:DLCaptureJob*)
      (progn (EL:DLCaptureCleanup *EL:DLCaptureJob*) (setq *EL:DLCaptureJob* nil)))
    (EL:DLFail "图例任务启动失败，编辑内容保留。")) (progn (EL:PerfCount "device-legend-builds" 1) T)))
(defun EL:DLCaptureStart (snapshot entry entity / root token folder dwg)
  (EL:Require (= (getvar "SDI") 0) "请使用多图纸模式（SDI=0）后登记图形。")
  (EL:Require (not *EL:DLCaptureJob*) "上一次图形登记尚未完成，请先返回设备库。")
  (setq root (EL:Get 'root snapshot) token (EL:DLOperationID) folder (strcat root ".staging/" token)
    dwg (strcat folder "/block.dwg"))
  (EL:Require (and (EL:DLMkdir (strcat root ".staging")) (EL:DLFolderClaim folder)) "临时图形目录不可写。")
  (EL:Require (EL:DLExport entity dwg) "设备图形导出失败，编辑内容保留；设备库未写入。")
  (EL:DLCapturePublishJob snapshot entry token folder))
(defun EL:DLCaptureFile (snapshot entry / root token folder original copy)
  (EL:Require (and (= (getvar "SDI") 0) (not *EL:DLCaptureJob*) (> (EL:Get 'asset-revision entry) 0)
    (equal (EL:Get 'block-file entry) (strcat (EL:DLAssetPrefix entry) "block.dwg"))) "当前图形不能修复，请先登记有效图形。")
  (setq root (EL:Get 'root snapshot) token (EL:DLOperationID) folder (strcat root ".staging/" token)
    original (strcat root (EL:Get 'block-file entry)) copy (strcat folder "/block.dwg"))
  (EL:Require (and (EL:DLDWGValid original) (EL:DLMkdir (strcat root ".staging")) (EL:DLFolderClaim folder)
    (vl-file-copy original copy) (EL:DLFilesEqual original copy)) "库内图形无法读取或复制，原资料保留。")
  (EL:DLCapturePublishJob snapshot entry token folder))
(defun EL:DLCaptureCleanup (job / prefix path file)
  (setq prefix (strcat (EL:Get 'root (EL:Get 'snapshot job)) ".staging/" (EL:Get 'token job) "/"))
  (if (and (EL:DLToken (EL:Get 'token job)) (equal (EL:Get 'dwg job) (strcat prefix "block.dwg")))
    (foreach file '("block.dwg" "legend.sld" "complete.txt")
      (setq path (strcat prefix file)) (if (findfile path) (vl-catch-all-apply 'vl-file-delete (list path))))))
(defun EL:DLCaptureClose (job / document path result)
  (setq document (EL:Get 'temporary job))
  (cond ((not document) T)
    ((vl-catch-all-error-p (setq path (vl-catch-all-apply 'vla-get-FullName (list document)))) nil)
    ((not (and (equal (type path) 'STR)
      (equal (strcase (vl-string-translate "\\" "/" path)) (strcase (EL:Get 'dwg job))))) nil)
    (T (setq result (vl-catch-all-apply 'vla-Activate (list (EL:Get 'source job))))
      (if (not (vl-catch-all-error-p result)) (progn
        (setq result (vl-catch-all-apply 'vla-Close (list document :vlax-false))) (not (vl-catch-all-error-p result)))))))
(defun EL:DLCaptureResume (token / job status result)
  (setq job *EL:DLCaptureJob*)
  (if (and job (equal token (EL:Get 'token job)) (or (EL:Get 'failed job) (findfile (EL:Get 'marker job)))) (progn
    (setq status (if (not (EL:Get 'failed job)) (EL:DLReadText (EL:Get 'marker job))))
    (if (not (EL:DLCaptureClose job)) (princ "\n临时图纸尚未关闭；登记未完成，请返回来源图纸运行 ELDEVLIB 重试。")
    (progn (setq *EL:DLCaptureJob* nil)
    (if (and status (equal (vl-string-trim "\r\n" status) "DONE") (EL:DLDWGValid (EL:Get 'dwg job)) (EL:DLSLDSize (EL:Get 'slide job)))
      (setq result (EL:Put 'captured job (EL:Get 'entry job)))
      (progn (EL:DLCaptureCleanup job) (setq *EL:DLError* "图例生成未完成，编辑内容保留；可重新拾取。")))
    (if *EL:DLContinue* (apply *EL:DLContinue* (list result)) result))))))
(princ)

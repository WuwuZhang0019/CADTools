; Tianzheng XGWZ wire-label test retired after native CAD rejection.
; Date: 2026-10-14
; Manual XGWZ cannot select this TCH_WIREDIM2 annotation.
(defun c:TZXGWZTEST ()
  (princ "\n真实 CAD 已确认 XGWZ 无法选取 TCH_WIREDIM2 回路标注；此测试已停用。")
  (princ)
)
(defun c:TZXGWZCHECK ()
  (princ "\nXGWZ 回路标注测试已停用。")
  (princ)
)
(princ "\nXGWZ 回路标注测试已停用，不会修改图纸。")
(princ)
